ZTE-3GPLAT-Public-MIB DEFINITIONS ::= BEGIN
 	IMPORTS
 	      RowStatus
 	        FROM SNMPv2-TC
		  atca
			FROM ZTE-PLAT-SMI
	      rast
			FROM ZTE-PLAT-SMI
	      enterprises,IpAddress, Integer32, 
              OBJECT-TYPE,MODULE-IDENTITY
			FROM SNMPv2-SMI
              DisplayString
			FROM SNMPv2-TC;
            
-- Node definitions
-- 
-- 1.3.6.1.4.1.3902.6053.19.1.3.11		
    public MODULE-IDENTITY
        LAST-UPDATED	  "201906190000Z"                    
        ORGANIZATION    "rast working group,zte Telecom. Co." 
        CONTACT-INFO    ""
        DESCRIPTION     "The Module for zte rast Public."
        ::= { rast 11 }


-- 1.3.6.1.4.1.3902.6053.19.1.3.11
    trap-alarm   OBJECT IDENTIFIER ::= {public 1}
    trap-addinfo OBJECT IDENTIFIER ::= {public 2}
    trap-public OBJECT IDENTIFIER ::= {public 3}
    trap-var OBJECT IDENTIFIER ::= {public 4}
-- 1.3.6.1.4.1.3902.6053.19.1.3.11.3.1
    dwAlarmID OBJECT-TYPE
        SYNTAX Unsigned32
        ACCESS accessible-for-notify
        STATUS current
        DESCRIPTION 
            "Alarm ID"
        ::= {trap-public 1}

-- 1.3.6.1.4.1.3902.6053.19.1.3.11.3.2
    tAlarmTime OBJECT-TYPE
        SYNTAX DisplayString
        ACCESS accessible-for-notify
        STATUS current
        DESCRIPTION 
            "Alarm time"
        ::= {trap-public 2}

-- 1.3.6.1.4.1.3902.6053.19.1.3.11.3.3
    ucAlarmFlag OBJECT-TYPE
        SYNTAX Unsigned32
        {
            alarm(1),
            restore(2),
            inform(3),
            synchronous(4)
        }
        ACCESS accessible-for-notify
        STATUS current
        DESCRIPTION 
            "Alarm flag"
        ::= {trap-public 3}

-- 1.3.6.1.4.1.3902.6053.19.1.3.11.3.4
    ucRestoreType OBJECT-TYPE
        SYNTAX Unsigned32
        {
            null(0),
            normal-restored(1),
            board-power-on-restored(2), 
            delete-restored(4), 
            bmc-reboot-restored(8),
            board-power-off-restored(16)
        }
        ACCESS accessible-for-notify
        STATUS current
        DESCRIPTION 
            "Alarm restore type"
        ::= {trap-public 4}

-- 1.3.6.1.4.1.3902.6053.19.1.3.11.3.5
    ucAlarmSeverity OBJECT-TYPE
        SYNTAX Unsigned32
        {
            critical(1),
            major(2),
            unknown(3),
            minor(4),
            inform(5)
        }
        ACCESS accessible-for-notify
        STATUS current
        DESCRIPTION 
            "Alarm severity"
        ::= {trap-public 5}

-- 1.3.6.1.4.1.3902.6053.19.1.3.11.3.6
    dwDeviceType OBJECT-TYPE
        SYNTAX Unsigned32
        {
            mainBoard(0),
            psu(1),
            fan(4),
            cpu(64),
            disk(65),
            memory(66),
            io-Module(67),
            gpu(68),
            smartCard(69),
            aiCard(70),
			mainBoardNicCard(71),
			mainBoardOcpCard(72),
            opticalModule(73),
            device(193)
        }
        ACCESS accessible-for-notify
        STATUS current
        DESCRIPTION 
            "Alarm device type"
        ::= {trap-public 6}

-- 1.3.6.1.4.1.3902.6053.19.1.3.11.3.7
    dwDeviceID OBJECT-TYPE
        SYNTAX Unsigned32
        ACCESS accessible-for-notify
        STATUS current
        DESCRIPTION 
            "Alarm device ID"
        ::= {trap-public 7}

-- 1.3.6.1.4.1.3902.6053.19.1.3.11.3.8
    ucSubSystem OBJECT-TYPE
        SYNTAX Unsigned32
        ACCESS accessible-for-notify
        STATUS current
        DESCRIPTION 
            "Reserved"
        ::= {trap-public 8}

-- 1.3.6.1.4.1.3902.6053.19.1.3.11.3.9
    wModule OBJECT-TYPE
        SYNTAX Unsigned32
        ACCESS accessible-for-notify
        STATUS current
        DESCRIPTION 
            "Reserved"
        ::= {trap-public 9}

-- 1.3.6.1.4.1.3902.6053.19.1.3.11.3.10
    wUnit OBJECT-TYPE
        SYNTAX Unsigned32
        ACCESS accessible-for-notify
        STATUS current
        DESCRIPTION 
            "Reserved"
        ::= {trap-public 10}

-- 1.3.6.1.4.1.3902.6053.19.1.3.11.3.11
    ucSUnit OBJECT-TYPE
        SYNTAX Unsigned32
        ACCESS accessible-for-notify
        STATUS current
        DESCRIPTION 
            "Reserved"
        ::= {trap-public 11}

-- 1.3.6.1.4.1.3902.6053.19.1.3.11.3.12
    dwCrcCode1 OBJECT-TYPE
        SYNTAX Unsigned32
        ACCESS accessible-for-notify
        STATUS current
        DESCRIPTION 
            "Alarm CRC code1"
        ::= {trap-public 12}

-- 1.3.6.1.4.1.3902.6053.19.1.3.11.3.13
    dwCrcCode2 OBJECT-TYPE
        SYNTAX Unsigned32
        ACCESS accessible-for-notify
        STATUS current
        DESCRIPTION 
            "Alarm CRC code2"
        ::= {trap-public 13}

-- 1.3.6.1.4.1.3902.6053.19.1.3.11.3.14
    dwCrcCode3 OBJECT-TYPE
        SYNTAX Unsigned32
        ACCESS accessible-for-notify
        STATUS current
        DESCRIPTION 
            "Alarm CRC code3"
        ::= {trap-public 14}

-- 1.3.6.1.4.1.3902.6053.19.1.3.11.3.15
    dwCrcCode4 OBJECT-TYPE
        SYNTAX Unsigned32
        ACCESS accessible-for-notify
        STATUS current
        DESCRIPTION 
            "Alarm CRC code4"
        ::= {trap-public 15}

-- 1.3.6.1.4.1.3902.6053.19.1.3.11.3.16
    wNtlvLen OBJECT-TYPE
        SYNTAX Unsigned32
        ACCESS accessible-for-notify
        STATUS current
        DESCRIPTION 
            "Reserved"
        ::= {trap-public 16}

-- 1.3.6.1.4.1.3902.6053.19.1.3.11.3.17
    wAlarmObj OBJECT-TYPE
        SYNTAX Unsigned32
        ACCESS accessible-for-notify
        STATUS current
        DESCRIPTION 
            "Reserved"
        ::= {trap-public 17}

-- 1.3.6.1.4.1.3902.6053.19.1.3.11.3.18
    wObjLen OBJECT-TYPE
        SYNTAX Unsigned32
        ACCESS accessible-for-notify
        STATUS current
        DESCRIPTION 
            "Reserved"
        ::= {trap-public 18}

-- 1.3.6.1.4.1.3902.6053.19.1.3.11.3.19
    acAlarmDesc OBJECT-TYPE
        SYNTAX DisplayString
        ACCESS accessible-for-notify
        STATUS current
        DESCRIPTION 
            "Alarm description"
        ::= {trap-public 19}

-- 1.3.6.1.4.1.3902.6053.19.1.3.11.3.20
    tAlarmUTCTime OBJECT-TYPE
        SYNTAX DisplayString
        ACCESS accessible-for-notify
        STATUS current
        DESCRIPTION 
            "Alarm UTC time"
        ::= {trap-public 20}

-- 1.3.6.1.4.1.3902.6053.19.1.3.11.4.1
    acTrapTime OBJECT-TYPE
        SYNTAX DisplayString
        ACCESS accessible-for-notify
        STATUS current
        DESCRIPTION 
            "Alarm time"
        ::= {trap-var 1}

-- 1.3.6.1.4.1.3902.6053.19.1.3.11.4.2
    acTrapEventSubject OBJECT-TYPE
        SYNTAX DisplayString
        ACCESS accessible-for-notify
        STATUS current
        DESCRIPTION 
            "Alarm event subject"
        ::= {trap-var 2}

-- 1.3.6.1.4.1.3902.6053.19.1.3.11.4.3
    acTrapSeverity OBJECT-TYPE
        SYNTAX DisplayString
        ACCESS accessible-for-notify
        STATUS current
        DESCRIPTION 
            "Alarm severity"
        ::= {trap-var 3}

-- 1.3.6.1.4.1.3902.6053.19.1.3.11.4.4
    acTrapDescription OBJECT-TYPE
        SYNTAX DisplayString
        ACCESS accessible-for-notify
        STATUS current
        DESCRIPTION 
            "Alarm description of a trap"
        ::= {trap-var 4}
		
-- 1.3.6.1.4.1.3902.6053.19.1.3.11.4.5
    acTrapProductSerial OBJECT-TYPE
        SYNTAX DisplayString
        ACCESS accessible-for-notify
        STATUS current
        DESCRIPTION 
            "Alarm product serial  number"
        ::= {trap-var 5}
-- 1.3.6.1.4.1.3902.6053.19.1.3.11.4.6
    acTrapState OBJECT-TYPE
        SYNTAX DisplayString
        ACCESS accessible-for-notify
        STATUS current
        DESCRIPTION 
            "Alarm state"
        ::= {trap-var 6}	

-- 1.3.6.1.4.1.3902.6053.19.1.3.11.4.7
    acTrapDeviceSN OBJECT-TYPE
        SYNTAX DisplayString
        ACCESS accessible-for-notify
        STATUS current
        DESCRIPTION 
            "Alarm device serial number"
        ::= {trap-var 7}
		
-- 1.3.6.1.4.1.3902.6053.19.1.3.11.4.8
    acTrapAddInform OBJECT-TYPE
        SYNTAX DisplayString
        ACCESS accessible-for-notify
        STATUS current
        DESCRIPTION 
            "Alarm additional information"
        ::= {trap-var 8}	

-- 1.3.6.1.4.1.3902.6053.19.1.3.11.4.9
    dwTrapIndex OBJECT-TYPE
        SYNTAX Unsigned32
        ACCESS accessible-for-notify
        STATUS current
        DESCRIPTION 
            "Alarm sequence"
        ::= {trap-var 9}
		
-- 1.3.6.1.4.1.3902.6053.19.1.3.11.1.23050
    trap-23050-addinfo OBJECT IDENTIFIER ::= {trap-addinfo 23050}

-- 1.3.6.1.4.1.3902.6053.19.1.3.11.2.23050.1
    trap-23050-ucFruId OBJECT-TYPE
        SYNTAX Unsigned32
        ACCESS accessible-for-notify
        STATUS current
        DESCRIPTION 
            "FRU ID"
        ::= {trap-23050-addinfo 1}

-- 1.3.6.1.4.1.3902.6053.19.1.3.11.2.23050.3
    trap-23050-ucGeneric8Offset OBJECT-TYPE
        SYNTAX Unsigned32
        ACCESS accessible-for-notify
        STATUS current
        DESCRIPTION 
            "Generic event state (type3)"
        ::= {trap-23050-addinfo 3}

-- 1.3.6.1.4.1.3902.6053.19.1.3.11.2.23050.5
    trap-23050-aucSensorName OBJECT-TYPE
        SYNTAX DisplayString
        ACCESS accessible-for-notify
        STATUS current
        DESCRIPTION 
            "Sensor name"
        ::= {trap-23050-addinfo 5}

-- 1.3.6.1.4.1.3902.6053.19.1.3.11.1.23050
    trapFanDeviceAbsent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-23050-ucFruId, trap-23050-ucGeneric8Offset, trap-23050-aucSensorName, acTrapTime, acTrapEventSubject, acTrapSeverity, acTrapDescription, acTrapProductSerial, acTrapState, acTrapDeviceSN, acTrapAddInform, dwTrapIndex
		                                        }
		STATUS			current
		DESCRIPTION		"Fan device absent."
		::=  {  trap-alarm 23050}

-- 1.3.6.1.4.1.3902.6053.19.1.3.11.1.23050
    trap-23050-reasoninfo OBJECT IDENTIFIER ::= {trap-alarm 23050}

-- 1.3.6.1.4.1.3902.6053.19.1.3.11.1.23050.1
    trapFanDeviceStatusAbsent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-23050-ucFruId, trap-23050-ucGeneric8Offset, trap-23050-aucSensorName, acTrapTime, acTrapEventSubject, acTrapSeverity, acTrapDescription, acTrapProductSerial, acTrapState, acTrapDeviceSN, acTrapAddInform, dwTrapIndex
		                                        }
		STATUS			current
		DESCRIPTION		"Fan device absent."
		::=  {  trap-23050-reasoninfo 1}

-- 1.3.6.1.4.1.3902.6053.19.1.3.11.1.23051
    trap-23051-addinfo OBJECT IDENTIFIER ::= {trap-addinfo 23051}

-- 1.3.6.1.4.1.3902.6053.19.1.3.11.2.23051.1
    trap-23051-ucFruId OBJECT-TYPE
        SYNTAX Unsigned32
        ACCESS accessible-for-notify
        STATUS current
        DESCRIPTION 
            "FRU ID"
        ::= {trap-23051-addinfo 1}

-- 1.3.6.1.4.1.3902.6053.19.1.3.11.2.23051.3
    trap-23051-ucGeneric8Offset OBJECT-TYPE
        SYNTAX Unsigned32
        ACCESS accessible-for-notify
        STATUS current
        DESCRIPTION 
            "Generic event state (type3)"
        ::= {trap-23051-addinfo 3}

-- 1.3.6.1.4.1.3902.6053.19.1.3.11.2.23051.5
    trap-23051-aucSensorName OBJECT-TYPE
        SYNTAX DisplayString
        ACCESS accessible-for-notify
        STATUS current
        DESCRIPTION 
            "Sensor name"
        ::= {trap-23051-addinfo 5}

-- 1.3.6.1.4.1.3902.6053.19.1.3.11.1.23051
    trapPowerUnitAbsent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-23051-ucFruId, trap-23051-ucGeneric8Offset, trap-23051-aucSensorName, acTrapTime, acTrapEventSubject, acTrapSeverity, acTrapDescription, acTrapProductSerial, acTrapState, acTrapDeviceSN, acTrapAddInform, dwTrapIndex
		                                        }
		STATUS			current
		DESCRIPTION		"Power unit absent."
		::=  {  trap-alarm 23051}

-- 1.3.6.1.4.1.3902.6053.19.1.3.11.1.23051
    trap-23051-reasoninfo OBJECT IDENTIFIER ::= {trap-alarm 23051}

-- 1.3.6.1.4.1.3902.6053.19.1.3.11.1.23051.1
    trapPowerUnitStatusAbsent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-23051-ucFruId, trap-23051-ucGeneric8Offset, trap-23051-aucSensorName, acTrapTime, acTrapEventSubject, acTrapSeverity, acTrapDescription, acTrapProductSerial, acTrapState, acTrapDeviceSN, acTrapAddInform, dwTrapIndex
		                                        }
		STATUS			current
		DESCRIPTION		"Power unit absent."
		::=  {  trap-23051-reasoninfo 1}

-- 1.3.6.1.4.1.3902.6053.19.1.3.11.1.30721
    trap-30721-addinfo OBJECT IDENTIFIER ::= {trap-addinfo 30721}

-- 1.3.6.1.4.1.3902.6053.19.1.3.11.2.30721.1
    trap-30721-ucFruId OBJECT-TYPE
        SYNTAX Unsigned32
        ACCESS accessible-for-notify
        STATUS current
        DESCRIPTION 
            "FRU ID"
        ::= {trap-30721-addinfo 1}

-- 1.3.6.1.4.1.3902.6053.19.1.3.11.2.30721.5
    trap-30721-aucCurrentValue OBJECT-TYPE
        SYNTAX DisplayString
        ACCESS accessible-for-notify
        STATUS current
        DESCRIPTION 
            "Current value"
        ::= {trap-30721-addinfo 5}

-- 1.3.6.1.4.1.3902.6053.19.1.3.11.2.30721.6
    trap-30721-aucThresholdValue OBJECT-TYPE
        SYNTAX DisplayString
        ACCESS accessible-for-notify
        STATUS current
        DESCRIPTION 
            "Threshold value"
        ::= {trap-30721-addinfo 6}

-- 1.3.6.1.4.1.3902.6053.19.1.3.11.2.30721.7
    trap-30721-aucUnitStr OBJECT-TYPE
        SYNTAX DisplayString
        ACCESS accessible-for-notify
        STATUS current
        DESCRIPTION 
            "Unit"
        ::= {trap-30721-addinfo 7}

-- 1.3.6.1.4.1.3902.6053.19.1.3.11.2.30721.8
    trap-30721-aucSensorName OBJECT-TYPE
        SYNTAX DisplayString
        ACCESS accessible-for-notify
        STATUS current
        DESCRIPTION 
            "Sensor name"
        ::= {trap-30721-addinfo 8}

-- 1.3.6.1.4.1.3902.6053.19.1.3.11.1.30721
    trapTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-alarm 30721}

-- 1.3.6.1.4.1.3902.6053.19.1.3.11.1.30721
    trap-30721-reasoninfo OBJECT IDENTIFIER ::= {trap-alarm 30721}

-- 1.3.6.1.4.1.3902.6053.19.1.3.11.1.30721.0
    trapUnspecifiedTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 0}

-- 1.3.6.1.4.1.3902.6053.19.1.3.11.1.30721.1
    trapOtherTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 1}

-- 1.3.6.1.4.1.3902.6053.19.1.3.11.1.30721.2
    trapUnkownTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 2}

-- 1.3.6.1.4.1.3902.6053.19.1.3.11.1.30721.3
    trapProcessorTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 3}

-- 1.3.6.1.4.1.3902.6053.19.1.3.11.1.30721.4
    trapDiskTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 4}

-- 1.3.6.1.4.1.3902.6053.19.1.3.11.1.30721.5
    trapPeripheralTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 5}

-- 1.3.6.1.4.1.3902.6053.19.1.3.11.1.30721.6
    trapSystemManagementModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 6}

-- 1.3.6.1.4.1.3902.6053.19.1.3.11.1.30721.7
    trapSystemBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 7}

-- 1.3.6.1.4.1.3902.6053.19.1.3.11.1.30721.8
    trapMemoryTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 8}

-- 1.3.6.1.4.1.3902.6053.19.1.3.11.1.30721.9
    trapProcessorModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 9}

-- 1.3.6.1.4.1.3902.6053.19.1.3.11.1.30721.10
    trapPowerSupplyTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 10}

-- 1.3.6.1.4.1.3902.6053.19.1.3.11.1.30721.11
    trapADDINCardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 11}

-- 1.3.6.1.4.1.3902.6053.19.1.3.11.1.30721.12
    trapFrontPanelBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 12}

-- 1.3.6.1.4.1.3902.6053.19.1.3.11.1.30721.13
    trapBackPanelBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 13}

-- 1.3.6.1.4.1.3902.6053.19.1.3.11.1.30721.14
    trapPowerSystemBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 14}

-- 1.3.6.1.4.1.3902.6053.19.1.3.11.1.30721.15
    trapDriveBackplaneTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 15}

-- 1.3.6.1.4.1.3902.6053.19.1.3.11.1.30721.16
    trapSystemInternalExpansionBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 16}

-- 1.3.6.1.4.1.3902.6053.19.1.3.11.1.30721.17
    trapOtherSystemBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 17}

-- 1.3.6.1.4.1.3902.6053.19.1.3.11.1.30721.18
    trapProcessorBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 18}

-- 1.3.6.1.4.1.3902.6053.19.1.3.11.1.30721.19
    trapPowerUnitTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 19}

-- 1.3.6.1.4.1.3902.6053.19.1.3.11.1.30721.20
    trapPowerModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 20}

-- 1.3.6.1.4.1.3902.6053.19.1.3.11.1.30721.21
    trapPowerManagementBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 21}

-- 1.3.6.1.4.1.3902.6053.19.1.3.11.1.30721.22
    trapChassisBackPanelBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 22}

-- 1.3.6.1.4.1.3902.6053.19.1.3.11.1.30721.23
    trapSystemChassisTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 23}

-- 1.3.6.1.4.1.3902.6053.19.1.3.11.1.30721.24
    trapSUBChassisTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 24}

-- 1.3.6.1.4.1.3902.6053.19.1.3.11.1.30721.25
    trapOtherChassisBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 25}

-- 1.3.6.1.4.1.3902.6053.19.1.3.11.1.30721.26
    trapDiskDriveTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 26}

-- 1.3.6.1.4.1.3902.6053.19.1.3.11.1.30721.27
    trapPeripheralBayTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 27}

-- 1.3.6.1.4.1.3902.6053.19.1.3.11.1.30721.28
    trapDeviceBayTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 28}

-- 1.3.6.1.4.1.3902.6053.19.1.3.11.1.30721.29
    trapFanCoolingTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 29}

-- 1.3.6.1.4.1.3902.6053.19.1.3.11.1.30721.30
    trapCoolingUnitTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 30}

-- 1.3.6.1.4.1.3902.6053.19.1.3.11.1.30721.31
    trapCableInterconnectTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 31}

-- 1.3.6.1.4.1.3902.6053.19.1.3.11.1.30721.32
    trapMemoryDeviceTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 32}

-- 1.3.6.1.4.1.3902.6053.19.1.3.11.1.30721.33
    trapSystemManagementSoftwareTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 33}

-- 1.3.6.1.4.1.3902.6053.19.1.3.11.1.30721.34
    trapBiosTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 34}

-- 1.3.6.1.4.1.3902.6053.19.1.3.11.1.30721.35
    trapOperatingSystemTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 35}

-- 1.3.6.1.4.1.3902.6053.19.1.3.11.1.30721.36
    trapSystemBusTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 36}

-- 1.3.6.1.4.1.3902.6053.19.1.3.11.1.30721.37
    trapGroupTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 37}

-- 1.3.6.1.4.1.3902.6053.19.1.3.11.1.30721.38
    trapRemotManagementDeviceTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 38}

-- 1.3.6.1.4.1.3902.6053.19.1.3.11.1.30721.39
    trapExternalEnvironmentTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 39}

-- 1.3.6.1.4.1.3902.6053.19.1.3.11.1.30721.40
    trapBatteryTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 40}

-- 1.3.6.1.4.1.3902.6053.19.1.3.11.1.30721.41
    trapProcessBladeModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 41}

-- 1.3.6.1.4.1.3902.6053.19.1.3.11.1.30721.42
    trapConnectivitySwitchTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 42}

-- 1.3.6.1.4.1.3902.6053.19.1.3.11.1.30721.43
    trapProcessorMemoryModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 43}

-- 1.3.6.1.4.1.3902.6053.19.1.3.11.1.30721.44
    trapIOModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 44}

-- 1.3.6.1.4.1.3902.6053.19.1.3.11.1.30721.45
    trapProcessorIOModuleTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 45}

-- 1.3.6.1.4.1.3902.6053.19.1.3.11.1.30721.46
    trapMGMTControllerFirmwareTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 46}

-- 1.3.6.1.4.1.3902.6053.19.1.3.11.1.30721.47
    trapIPMIChannelTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 47}

-- 1.3.6.1.4.1.3902.6053.19.1.3.11.1.30721.48
    trapPCIBUSTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 48}

-- 1.3.6.1.4.1.3902.6053.19.1.3.11.1.30721.49
    trapPCIExpressBUSTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 49}

-- 1.3.6.1.4.1.3902.6053.19.1.3.11.1.30721.50
    trapSCSIBUSTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 50}

-- 1.3.6.1.4.1.3902.6053.19.1.3.11.1.30721.51
    trapSATASASBUSTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 51}

-- 1.3.6.1.4.1.3902.6053.19.1.3.11.1.30721.52
    trapProcessorFrontSideBUSTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 52}

-- 1.3.6.1.4.1.3902.6053.19.1.3.11.1.30721.53
    trapRealTimeClockTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 53}

-- 1.3.6.1.4.1.3902.6053.19.1.3.11.1.30721.54
    trapSystemFirmwareTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 54}

-- 1.3.6.1.4.1.3902.6053.19.1.3.11.1.30721.160
    trapMainBoardTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 160}

-- 1.3.6.1.4.1.3902.6053.19.1.3.11.1.30721.208
    trapNetPortTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 208}

-- 1.3.6.1.4.1.3902.6053.19.1.3.11.1.30721.209
    trapLogicalDiskTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 209}

-- 1.3.6.1.4.1.3902.6053.19.1.3.11.1.30721.210
    trapStorageCTRLTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 210}

-- 1.3.6.1.4.1.3902.6053.19.1.3.11.1.30721.272
    trapNICSFPTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 272}

-- 1.3.6.1.4.1.3902.6053.19.1.3.11.1.30721.273
    trapOCPSFPTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 273}

-- 1.3.6.1.4.1.3902.6053.19.1.3.11.1.30721.275
    trapSNICSFPTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 28}

-- 1.3.6.1.4.1.3902.6053.19.1.3.11.1.30721.277
    trapDPUT100TemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 277}

-- 1.3.6.1.4.1.3902.6053.19.1.3.11.1.30721.278
    trapDPUT200TemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 278}

-- 1.3.6.1.4.1.3902.6053.19.1.3.11.1.30721.279
    trapBSC25GTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 279}

-- 1.3.6.1.4.1.3902.6053.19.1.3.11.1.30721.281
    trapNEOTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 281}

-- 1.3.6.1.4.1.3902.6053.19.1.3.11.1.30721.282
    trapZiJinTemperatureIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30721-ucFruId, trap-30721-aucCurrentValue, trap-30721-aucThresholdValue, trap-30721-aucUnitStr, trap-30721-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-critical threshold."
		::=  {  trap-30721-reasoninfo 282}

-- 1.3.6.1.4.1.3902.6053.19.1.3.11.1.30722
    trap-30722-addinfo OBJECT IDENTIFIER ::= {trap-addinfo 30722}

-- 1.3.6.1.4.1.3902.6053.19.1.3.11.2.30722.1
    trap-30722-ucFruId OBJECT-TYPE
        SYNTAX Unsigned32
        ACCESS accessible-for-notify
        STATUS current
        DESCRIPTION 
            "FRU ID"
        ::= {trap-30722-addinfo 1}

-- 1.3.6.1.4.1.3902.6053.19.1.3.11.2.30722.5
    trap-30722-aucCurrentValue OBJECT-TYPE
        SYNTAX DisplayString
        ACCESS accessible-for-notify
        STATUS current
        DESCRIPTION 
            "Current value"
        ::= {trap-30722-addinfo 5}

-- 1.3.6.1.4.1.3902.6053.19.1.3.11.2.30722.6
    trap-30722-aucThresholdValue OBJECT-TYPE
        SYNTAX DisplayString
        ACCESS accessible-for-notify
        STATUS current
        DESCRIPTION 
            "Threshold value"
        ::= {trap-30722-addinfo 6}

-- 1.3.6.1.4.1.3902.6053.19.1.3.11.2.30722.7
    trap-30722-aucUnitStr OBJECT-TYPE
        SYNTAX DisplayString
        ACCESS accessible-for-notify
        STATUS current
        DESCRIPTION 
            "Unit"
        ::= {trap-30722-addinfo 7}

-- 1.3.6.1.4.1.3902.6053.19.1.3.11.2.30722.8
    trap-30722-aucSensorName OBJECT-TYPE
        SYNTAX DisplayString
        ACCESS accessible-for-notify
        STATUS current
        DESCRIPTION 
            "Sensor name"
        ::= {trap-30722-addinfo 8}

-- 1.3.6.1.4.1.3902.6053.19.1.3.11.1.30722
    trapTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-alarm 30722}

-- 1.3.6.1.4.1.3902.6053.19.1.3.11.1.30722
    trap-30722-reasoninfo OBJECT IDENTIFIER ::= {trap-alarm 30722}

-- 1.3.6.1.4.1.3902.6053.19.1.3.11.1.30722.0
    trapUnspecifiedTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 0}

-- 1.3.6.1.4.1.3902.6053.19.1.3.11.1.30722.1
    trapOtherTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 1}

-- 1.3.6.1.4.1.3902.6053.19.1.3.11.1.30722.2
    trapUnkownTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 2}

-- 1.3.6.1.4.1.3902.6053.19.1.3.11.1.30722.3
    trapProcessorTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 3}

-- 1.3.6.1.4.1.3902.6053.19.1.3.11.1.30722.4
    trapDiskTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 4}

-- 1.3.6.1.4.1.3902.6053.19.1.3.11.1.30722.5
    trapPeripheralTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 5}

-- 1.3.6.1.4.1.3902.6053.19.1.3.11.1.30722.6
    trapSystemManagementModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 6}

-- 1.3.6.1.4.1.3902.6053.19.1.3.11.1.30722.7
    trapSystemBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 7}

-- 1.3.6.1.4.1.3902.6053.19.1.3.11.1.30722.8
    trapMemoryTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 8}

-- 1.3.6.1.4.1.3902.6053.19.1.3.11.1.30722.9
    trapProcessorModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 9}

-- 1.3.6.1.4.1.3902.6053.19.1.3.11.1.30722.10
    trapPowerSupplyTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 10}

-- 1.3.6.1.4.1.3902.6053.19.1.3.11.1.30722.11
    trapADDINCardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 11}

-- 1.3.6.1.4.1.3902.6053.19.1.3.11.1.30722.12
    trapFrontPanelBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 12}

-- 1.3.6.1.4.1.3902.6053.19.1.3.11.1.30722.13
    trapBackPanelBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 13}

-- 1.3.6.1.4.1.3902.6053.19.1.3.11.1.30722.14
    trapPowerSystemBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 14}

-- 1.3.6.1.4.1.3902.6053.19.1.3.11.1.30722.15
    trapDriveBackplaneTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 15}

-- 1.3.6.1.4.1.3902.6053.19.1.3.11.1.30722.16
    trapSystemInternalExpansionBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 16}

-- 1.3.6.1.4.1.3902.6053.19.1.3.11.1.30722.17
    trapOtherSystemBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 17}

-- 1.3.6.1.4.1.3902.6053.19.1.3.11.1.30722.18
    trapProcessorBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 18}

-- 1.3.6.1.4.1.3902.6053.19.1.3.11.1.30722.19
    trapPowerUnitTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 19}

-- 1.3.6.1.4.1.3902.6053.19.1.3.11.1.30722.20
    trapPowerModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 20}

-- 1.3.6.1.4.1.3902.6053.19.1.3.11.1.30722.21
    trapPowerManagementBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 21}

-- 1.3.6.1.4.1.3902.6053.19.1.3.11.1.30722.22
    trapChassisBackPanelBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 22}

-- 1.3.6.1.4.1.3902.6053.19.1.3.11.1.30722.23
    trapSystemChassisTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 23}

-- 1.3.6.1.4.1.3902.6053.19.1.3.11.1.30722.24
    trapSUBChassisTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 24}

-- 1.3.6.1.4.1.3902.6053.19.1.3.11.1.30722.25
    trapOtherChassisBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 25}

-- 1.3.6.1.4.1.3902.6053.19.1.3.11.1.30722.26
    trapDiskDriveTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 26}

-- 1.3.6.1.4.1.3902.6053.19.1.3.11.1.30722.27
    trapPeripheralBayTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 27}

-- 1.3.6.1.4.1.3902.6053.19.1.3.11.1.30722.28
    trapDeviceBayTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 28}

-- 1.3.6.1.4.1.3902.6053.19.1.3.11.1.30722.29
    trapFanCoolingTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 29}

-- 1.3.6.1.4.1.3902.6053.19.1.3.11.1.30722.30
    trapCoolingUnitTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 30}

-- 1.3.6.1.4.1.3902.6053.19.1.3.11.1.30722.31
    trapCableInterconnectTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 31}

-- 1.3.6.1.4.1.3902.6053.19.1.3.11.1.30722.32
    trapMemoryDeviceTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 32}

-- 1.3.6.1.4.1.3902.6053.19.1.3.11.1.30722.33
    trapSystemManagementSoftwareTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 33}

-- 1.3.6.1.4.1.3902.6053.19.1.3.11.1.30722.34
    trapBiosTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 34}

-- 1.3.6.1.4.1.3902.6053.19.1.3.11.1.30722.35
    trapOperatingSystemTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 35}

-- 1.3.6.1.4.1.3902.6053.19.1.3.11.1.30722.36
    trapSystemBusTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 36}

-- 1.3.6.1.4.1.3902.6053.19.1.3.11.1.30722.37
    trapGroupTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 37}

-- 1.3.6.1.4.1.3902.6053.19.1.3.11.1.30722.38
    trapRemotManagementDeviceTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 38}

-- 1.3.6.1.4.1.3902.6053.19.1.3.11.1.30722.39
    trapExternalEnvironmentTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 39}

-- 1.3.6.1.4.1.3902.6053.19.1.3.11.1.30722.40
    trapBatteryTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 40}

-- 1.3.6.1.4.1.3902.6053.19.1.3.11.1.30722.41
    trapProcessBladeModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 41}

-- 1.3.6.1.4.1.3902.6053.19.1.3.11.1.30722.42
    trapConnectivitySwitchTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 42}

-- 1.3.6.1.4.1.3902.6053.19.1.3.11.1.30722.43
    trapProcessorMemoryModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 43}

-- 1.3.6.1.4.1.3902.6053.19.1.3.11.1.30722.44
    trapIOModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 44}

-- 1.3.6.1.4.1.3902.6053.19.1.3.11.1.30722.45
    trapProcessorIOModuleTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 45}

-- 1.3.6.1.4.1.3902.6053.19.1.3.11.1.30722.46
    trapMGMTControllerFirmwareTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 46}

-- 1.3.6.1.4.1.3902.6053.19.1.3.11.1.30722.47
    trapIPMIChannelTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 47}

-- 1.3.6.1.4.1.3902.6053.19.1.3.11.1.30722.48
    trapPCIBUSTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 48}

-- 1.3.6.1.4.1.3902.6053.19.1.3.11.1.30722.49
    trapPCIExpressBUSTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 49}

-- 1.3.6.1.4.1.3902.6053.19.1.3.11.1.30722.50
    trapSCSIBUSTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 50}

-- 1.3.6.1.4.1.3902.6053.19.1.3.11.1.30722.51
    trapSATASASBUSTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 51}

-- 1.3.6.1.4.1.3902.6053.19.1.3.11.1.30722.52
    trapProcessorFrontSideBUSTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 52}

-- 1.3.6.1.4.1.3902.6053.19.1.3.11.1.30722.53
    trapRealTimeClockTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 53}

-- 1.3.6.1.4.1.3902.6053.19.1.3.11.1.30722.54
    trapSystemFirmwareTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 54}

-- 1.3.6.1.4.1.3902.6053.19.1.3.11.1.30722.160
    trapMainBoardTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 160}

-- 1.3.6.1.4.1.3902.6053.19.1.3.11.1.30722.208
    trapNetPortTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 208}

-- 1.3.6.1.4.1.3902.6053.19.1.3.11.1.30722.209
    trapLogicalDiskTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 209}

-- 1.3.6.1.4.1.3902.6053.19.1.3.11.1.30722.210
    trapStorageCTRLTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 210}

-- 1.3.6.1.4.1.3902.6053.19.1.3.11.1.30722.272
    trapNICSFPTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 272}

-- 1.3.6.1.4.1.3902.6053.19.1.3.11.1.30722.273
    trapOCPSFPTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 273}

-- 1.3.6.1.4.1.3902.6053.19.1.3.11.1.30722.275
    trapSNICSFPTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 28}

-- 1.3.6.1.4.1.3902.6053.19.1.3.11.1.30722.277
    trapDPUT100TemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 277}

-- 1.3.6.1.4.1.3902.6053.19.1.3.11.1.30722.278
    trapDPUT200TemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 278}

-- 1.3.6.1.4.1.3902.6053.19.1.3.11.1.30722.279
    trapBSC25GTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 279}

-- 1.3.6.1.4.1.3902.6053.19.1.3.11.1.30722.281
    trapNEOTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 281}

-- 1.3.6.1.4.1.3902.6053.19.1.3.11.1.30722.282
    trapZiJinTemperatureIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30722-ucFruId, trap-30722-aucCurrentValue, trap-30722-aucThresholdValue, trap-30722-aucUnitStr, trap-30722-aucSensorName, acTrapTime, acTrapEventSubject, acTrapSeverity, acTrapDescription, acTrapProductSerial, acTrapState, acTrapDeviceSN, acTrapAddInform, dwTrapIndex
		                                        }
		STATUS			current
		DESCRIPTION		"Temperature is lower than lower-critical threshold."
		::=  {  trap-30722-reasoninfo 282}

-- 1.3.6.1.4.1.3902.6053.19.1.3.11.1.30723
    trap-30723-addinfo OBJECT IDENTIFIER ::= {trap-addinfo 30723}

-- 1.3.6.1.4.1.3902.6053.19.1.3.11.2.30723.1
    trap-30723-ucFruId OBJECT-TYPE
        SYNTAX Unsigned32
        ACCESS accessible-for-notify
        STATUS current
        DESCRIPTION 
            "FRU ID"
        ::= {trap-30723-addinfo 1}

-- 1.3.6.1.4.1.3902.6053.19.1.3.11.2.30723.5
    trap-30723-aucCurrentValue OBJECT-TYPE
        SYNTAX DisplayString
        ACCESS accessible-for-notify
        STATUS current
        DESCRIPTION 
            "Current value"
        ::= {trap-30723-addinfo 5}

-- 1.3.6.1.4.1.3902.6053.19.1.3.11.2.30723.6
    trap-30723-aucThresholdValue OBJECT-TYPE
        SYNTAX DisplayString
        ACCESS accessible-for-notify
        STATUS current
        DESCRIPTION 
            "Threshold value"
        ::= {trap-30723-addinfo 6}

-- 1.3.6.1.4.1.3902.6053.19.1.3.11.2.30723.7
    trap-30723-aucUnitStr OBJECT-TYPE
        SYNTAX DisplayString
        ACCESS accessible-for-notify
        STATUS current
        DESCRIPTION 
            "Unit"
        ::= {trap-30723-addinfo 7}

-- 1.3.6.1.4.1.3902.6053.19.1.3.11.2.30723.8
    trap-30723-aucSensorName OBJECT-TYPE
        SYNTAX DisplayString
        ACCESS accessible-for-notify
        STATUS current
        DESCRIPTION 
            "ISensor name"
        ::= {trap-30723-addinfo 8}

-- 1.3.6.1.4.1.3902.6053.19.1.3.11.1.30723
    trapTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-alarm 30723}

-- 1.3.6.1.4.1.3902.6053.19.1.3.11.1.30723
    trap-30723-reasoninfo OBJECT IDENTIFIER ::= {trap-alarm 30723}

-- 1.3.6.1.4.1.3902.6053.19.1.3.11.1.30723.0
    trapUnspecifiedTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 0}

-- 1.3.6.1.4.1.3902.6053.19.1.3.11.1.30723.1
    trapOtherTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 1}

-- 1.3.6.1.4.1.3902.6053.19.1.3.11.1.30723.2
    trapUnkownTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 2}

-- 1.3.6.1.4.1.3902.6053.19.1.3.11.1.30723.3
    trapProcessorTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 3}

-- 1.3.6.1.4.1.3902.6053.19.1.3.11.1.30723.4
    trapDiskTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 4}

-- 1.3.6.1.4.1.3902.6053.19.1.3.11.1.30723.5
    trapPeripheralTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 5}

-- 1.3.6.1.4.1.3902.6053.19.1.3.11.1.30723.6
    trapSystemManagementModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 6}

-- 1.3.6.1.4.1.3902.6053.19.1.3.11.1.30723.7
    trapSystemBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 7}

-- 1.3.6.1.4.1.3902.6053.19.1.3.11.1.30723.8
    trapMemoryTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 8}

-- 1.3.6.1.4.1.3902.6053.19.1.3.11.1.30723.9
    trapProcessorModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 9}

-- 1.3.6.1.4.1.3902.6053.19.1.3.11.1.30723.10
    trapPowerSupplyTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 10}

-- 1.3.6.1.4.1.3902.6053.19.1.3.11.1.30723.11
    trapADDINCardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 11}

-- 1.3.6.1.4.1.3902.6053.19.1.3.11.1.30723.12
    trapFrontPanelBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 12}

-- 1.3.6.1.4.1.3902.6053.19.1.3.11.1.30723.13
    trapBackPanelBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 13}

-- 1.3.6.1.4.1.3902.6053.19.1.3.11.1.30723.14
    trapPowerSystemBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 14}

-- 1.3.6.1.4.1.3902.6053.19.1.3.11.1.30723.15
    trapDriveBackplaneTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 15}

-- 1.3.6.1.4.1.3902.6053.19.1.3.11.1.30723.16
    trapSystemInternalExpansionBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 16}

-- 1.3.6.1.4.1.3902.6053.19.1.3.11.1.30723.17
    trapOtherSystemBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 17}

-- 1.3.6.1.4.1.3902.6053.19.1.3.11.1.30723.18
    trapProcessorBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 18}

-- 1.3.6.1.4.1.3902.6053.19.1.3.11.1.30723.19
    trapPowerUnitTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 19}

-- 1.3.6.1.4.1.3902.6053.19.1.3.11.1.30723.20
    trapPowerModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 20}

-- 1.3.6.1.4.1.3902.6053.19.1.3.11.1.30723.21
    trapPowerManagementBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 21}

-- 1.3.6.1.4.1.3902.6053.19.1.3.11.1.30723.22
    trapChassisBackPanelBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 22}

-- 1.3.6.1.4.1.3902.6053.19.1.3.11.1.30723.23
    trapSystemChassisTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 23}

-- 1.3.6.1.4.1.3902.6053.19.1.3.11.1.30723.24
    trapSUBChassisTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 24}

-- 1.3.6.1.4.1.3902.6053.19.1.3.11.1.30723.25
    trapOtherChassisBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 25}

-- 1.3.6.1.4.1.3902.6053.19.1.3.11.1.30723.26
    trapDiskDriveTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 26}

-- 1.3.6.1.4.1.3902.6053.19.1.3.11.1.30723.27
    trapPeripheralBayTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 27}

-- 1.3.6.1.4.1.3902.6053.19.1.3.11.1.30723.28
    trapDeviceBayTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 28}

-- 1.3.6.1.4.1.3902.6053.19.1.3.11.1.30723.29
    trapFanCoolingTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 29}

-- 1.3.6.1.4.1.3902.6053.19.1.3.11.1.30723.30
    trapCoolingUnitTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 30}

-- 1.3.6.1.4.1.3902.6053.19.1.3.11.1.30723.31
    trapCableInterconnectTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 31}

-- 1.3.6.1.4.1.3902.6053.19.1.3.11.1.30723.32
    trapMemoryDeviceTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 32}

-- 1.3.6.1.4.1.3902.6053.19.1.3.11.1.30723.33
    trapSystemManagementSoftwareTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 33}

-- 1.3.6.1.4.1.3902.6053.19.1.3.11.1.30723.34
    trapBiosTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 34}

-- 1.3.6.1.4.1.3902.6053.19.1.3.11.1.30723.35
    trapOperatingSystemTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 35}

-- 1.3.6.1.4.1.3902.6053.19.1.3.11.1.30723.36
    trapSystemBusTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 36}

-- 1.3.6.1.4.1.3902.6053.19.1.3.11.1.30723.37
    trapGroupTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 37}

-- 1.3.6.1.4.1.3902.6053.19.1.3.11.1.30723.38
    trapRemotManagementDeviceTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 38}

-- 1.3.6.1.4.1.3902.6053.19.1.3.11.1.30723.39
    trapExternalEnvironmentTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 39}

-- 1.3.6.1.4.1.3902.6053.19.1.3.11.1.30723.40
    trapBatteryTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 40}

-- 1.3.6.1.4.1.3902.6053.19.1.3.11.1.30723.41
    trapProcessBladeModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 41}

-- 1.3.6.1.4.1.3902.6053.19.1.3.11.1.30723.42
    trapConnectivitySwitchTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 42}

-- 1.3.6.1.4.1.3902.6053.19.1.3.11.1.30723.43
    trapProcessorMemoryModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 43}

-- 1.3.6.1.4.1.3902.6053.19.1.3.11.1.30723.44
    trapIOModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 44}

-- 1.3.6.1.4.1.3902.6053.19.1.3.11.1.30723.45
    trapProcessorIOModuleTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 45}

-- 1.3.6.1.4.1.3902.6053.19.1.3.11.1.30723.46
    trapMGMTControllerFirmwareTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 46}

-- 1.3.6.1.4.1.3902.6053.19.1.3.11.1.30723.47
    trapIPMIChannelTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 47}

-- 1.3.6.1.4.1.3902.6053.19.1.3.11.1.30723.48
    trapPCIBUSTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 48}

-- 1.3.6.1.4.1.3902.6053.19.1.3.11.1.30723.49
    trapPCIExpressBUSTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 49}

-- 1.3.6.1.4.1.3902.6053.19.1.3.11.1.30723.50
    trapSCSIBUSTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 50}

-- 1.3.6.1.4.1.3902.6053.19.1.3.11.1.30723.51
    trapSATASASBUSTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 51}

-- 1.3.6.1.4.1.3902.6053.19.1.3.11.1.30723.52
    trapProcessorFrontSideBUSTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 52}

-- 1.3.6.1.4.1.3902.6053.19.1.3.11.1.30723.53
    trapRealTimeClockTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 53}

-- 1.3.6.1.4.1.3902.6053.19.1.3.11.1.30723.54
    trapSystemFirmwareTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 54}

-- 1.3.6.1.4.1.3902.6053.19.1.3.11.1.30723.160
    trapMainBoardTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 160}

-- 1.3.6.1.4.1.3902.6053.19.1.3.11.1.30723.208
    trapNetPortTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 208}

-- 1.3.6.1.4.1.3902.6053.19.1.3.11.1.30723.209
    trapLogicalDiskTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 209}

-- 1.3.6.1.4.1.3902.6053.19.1.3.11.1.30723.210
    trapStorageCTRLTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 210}

-- 1.3.6.1.4.1.3902.6053.19.1.3.11.1.30723.272
    trapNICSFPTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 272}

-- 1.3.6.1.4.1.3902.6053.19.1.3.11.1.30723.273
    trapOCPSFPTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 273}

-- 1.3.6.1.4.1.3902.6053.19.1.3.11.1.30723.275
    trapSNICSFPTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 28}

-- 1.3.6.1.4.1.3902.6053.19.1.3.11.1.30723.277
    trapDPUT100TemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 277}

-- 1.3.6.1.4.1.3902.6053.19.1.3.11.1.30723.278
    trapDPUT200TemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 278}

-- 1.3.6.1.4.1.3902.6053.19.1.3.11.1.30723.279
    trapBSC25GTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 279}

-- 1.3.6.1.4.1.3902.6053.19.1.3.11.1.30723.281
    trapNEOTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 281}

-- 1.3.6.1.4.1.3902.6053.19.1.3.11.1.30723.282
    trapZiJinTemperatureIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30723-ucFruId, trap-30723-aucCurrentValue, trap-30723-aucThresholdValue, trap-30723-aucUnitStr, trap-30723-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30723-reasoninfo 282}

-- 1.3.6.1.4.1.3902.6053.19.1.3.11.1.30724
    trap-30724-addinfo OBJECT IDENTIFIER ::= {trap-addinfo 30724}

-- 1.3.6.1.4.1.3902.6053.19.1.3.11.2.30724.1
    trap-30724-ucFruId OBJECT-TYPE
        SYNTAX Unsigned32
        ACCESS accessible-for-notify
        STATUS current
        DESCRIPTION 
            "FRU ID"
        ::= {trap-30724-addinfo 1}

-- 1.3.6.1.4.1.3902.6053.19.1.3.11.2.30724.5
    trap-30724-aucCurrentValue OBJECT-TYPE
        SYNTAX DisplayString
        ACCESS accessible-for-notify
        STATUS current
        DESCRIPTION 
            "Current value"
        ::= {trap-30724-addinfo 5}

-- 1.3.6.1.4.1.3902.6053.19.1.3.11.2.30724.6
    trap-30724-aucThresholdValue OBJECT-TYPE
        SYNTAX DisplayString
        ACCESS accessible-for-notify
        STATUS current
        DESCRIPTION 
            "Threshold value"
        ::= {trap-30724-addinfo 6}

-- 1.3.6.1.4.1.3902.6053.19.1.3.11.2.30724.7
    trap-30724-aucUnitStr OBJECT-TYPE
        SYNTAX DisplayString
        ACCESS accessible-for-notify
        STATUS current
        DESCRIPTION 
            "Unit"
        ::= {trap-30724-addinfo 7}

-- 1.3.6.1.4.1.3902.6053.19.1.3.11.2.30724.8
    trap-30724-aucSensorName OBJECT-TYPE
        SYNTAX DisplayString
        ACCESS accessible-for-notify
        STATUS current
        DESCRIPTION 
            "Sensor name"
        ::= {trap-30724-addinfo 8}

-- 1.3.6.1.4.1.3902.6053.19.1.3.11.1.30724
    trapTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-critical threshold"
		::=  {  trap-alarm 30724}

-- 1.3.6.1.4.1.3902.6053.19.1.3.11.1.30724
    trap-30724-reasoninfo OBJECT IDENTIFIER ::= {trap-alarm 30724}

-- 1.3.6.1.4.1.3902.6053.19.1.3.11.1.30724.0
    trapUnspecifiedTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 0}

-- 1.3.6.1.4.1.3902.6053.19.1.3.11.1.30724.1
    trapOtherTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 1}

-- 1.3.6.1.4.1.3902.6053.19.1.3.11.1.30724.2
    trapUnkownTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 2}

-- 1.3.6.1.4.1.3902.6053.19.1.3.11.1.30724.3
    trapProcessorTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 3}

-- 1.3.6.1.4.1.3902.6053.19.1.3.11.1.30724.4
    trapDiskTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 4}

-- 1.3.6.1.4.1.3902.6053.19.1.3.11.1.30724.5
    trapPeripheralTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 5}

-- 1.3.6.1.4.1.3902.6053.19.1.3.11.1.30724.6
    trapSystemManagementModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 6}

-- 1.3.6.1.4.1.3902.6053.19.1.3.11.1.30724.7
    trapSystemBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 7}

-- 1.3.6.1.4.1.3902.6053.19.1.3.11.1.30724.8
    trapMemoryTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 8}

-- 1.3.6.1.4.1.3902.6053.19.1.3.11.1.30724.9
    trapProcessorModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 9}

-- 1.3.6.1.4.1.3902.6053.19.1.3.11.1.30724.10
    trapPowerSupplyTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 10}

-- 1.3.6.1.4.1.3902.6053.19.1.3.11.1.30724.11
    trapADDINCardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 11}

-- 1.3.6.1.4.1.3902.6053.19.1.3.11.1.30724.12
    trapFrontPanelBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 12}

-- 1.3.6.1.4.1.3902.6053.19.1.3.11.1.30724.13
    trapBackPanelBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 13}

-- 1.3.6.1.4.1.3902.6053.19.1.3.11.1.30724.14
    trapPowerSystemBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 14}

-- 1.3.6.1.4.1.3902.6053.19.1.3.11.1.30724.15
    trapDriveBackplaneTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 15}

-- 1.3.6.1.4.1.3902.6053.19.1.3.11.1.30724.16
    trapSystemInternalExpansionBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 16}

-- 1.3.6.1.4.1.3902.6053.19.1.3.11.1.30724.17
    trapOtherSystemBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 17}

-- 1.3.6.1.4.1.3902.6053.19.1.3.11.1.30724.18
    trapProcessorBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 18}

-- 1.3.6.1.4.1.3902.6053.19.1.3.11.1.30724.19
    trapPowerUnitTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 19}

-- 1.3.6.1.4.1.3902.6053.19.1.3.11.1.30724.20
    trapPowerModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 20}

-- 1.3.6.1.4.1.3902.6053.19.1.3.11.1.30724.21
    trapPowerManagementBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 21}

-- 1.3.6.1.4.1.3902.6053.19.1.3.11.1.30724.22
    trapChassisBackPanelBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 22}

-- 1.3.6.1.4.1.3902.6053.19.1.3.11.1.30724.23
    trapSystemChassisTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 23}

-- 1.3.6.1.4.1.3902.6053.19.1.3.11.1.30724.24
    trapSUBChassisTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 24}

-- 1.3.6.1.4.1.3902.6053.19.1.3.11.1.30724.25
    trapOtherChassisBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 25}

-- 1.3.6.1.4.1.3902.6053.19.1.3.11.1.30724.26
    trapDiskDriveTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 26}

-- 1.3.6.1.4.1.3902.6053.19.1.3.11.1.30724.27
    trapPeripheralBayTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 27}

-- 1.3.6.1.4.1.3902.6053.19.1.3.11.1.30724.28
    trapDeviceBayTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 28}

-- 1.3.6.1.4.1.3902.6053.19.1.3.11.1.30724.29
    trapFanCoolingTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 29}

-- 1.3.6.1.4.1.3902.6053.19.1.3.11.1.30724.30
    trapCoolingUnitTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 30}

-- 1.3.6.1.4.1.3902.6053.19.1.3.11.1.30724.31
    trapCableInterconnectTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 31}

-- 1.3.6.1.4.1.3902.6053.19.1.3.11.1.30724.32
    trapMemoryDeviceTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 32}

-- 1.3.6.1.4.1.3902.6053.19.1.3.11.1.30724.33
    trapSystemManagementSoftwareTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 33}

-- 1.3.6.1.4.1.3902.6053.19.1.3.11.1.30724.34
    trapBiosTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 34}

-- 1.3.6.1.4.1.3902.6053.19.1.3.11.1.30724.35
    trapOperatingSystemTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 35}

-- 1.3.6.1.4.1.3902.6053.19.1.3.11.1.30724.36
    trapSystemBusTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 36}

-- 1.3.6.1.4.1.3902.6053.19.1.3.11.1.30724.37
    trapGroupTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 37}

-- 1.3.6.1.4.1.3902.6053.19.1.3.11.1.30724.38
    trapRemotManagementDeviceTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 38}

-- 1.3.6.1.4.1.3902.6053.19.1.3.11.1.30724.39
    trapExternalEnvironmentTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 39}

-- 1.3.6.1.4.1.3902.6053.19.1.3.11.1.30724.40
    trapBatteryTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 40}

-- 1.3.6.1.4.1.3902.6053.19.1.3.11.1.30724.41
    trapProcessBladeModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 41}

-- 1.3.6.1.4.1.3902.6053.19.1.3.11.1.30724.42
    trapConnectivitySwitchTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 42}

-- 1.3.6.1.4.1.3902.6053.19.1.3.11.1.30724.43
    trapProcessorMemoryModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 43}

-- 1.3.6.1.4.1.3902.6053.19.1.3.11.1.30724.44
    trapIOModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 44}

-- 1.3.6.1.4.1.3902.6053.19.1.3.11.1.30724.45
    trapProcessorIOModuleTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 45}

-- 1.3.6.1.4.1.3902.6053.19.1.3.11.1.30724.46
    trapMGMTControllerFirmwareTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 46}

-- 1.3.6.1.4.1.3902.6053.19.1.3.11.1.30724.47
    trapIPMIChannelTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 47}

-- 1.3.6.1.4.1.3902.6053.19.1.3.11.1.30724.48
    trapPCIBUSTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 48}

-- 1.3.6.1.4.1.3902.6053.19.1.3.11.1.30724.49
    trapPCIExpressBUSTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 49}

-- 1.3.6.1.4.1.3902.6053.19.1.3.11.1.30724.50
    trapSCSIBUSTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 50}

-- 1.3.6.1.4.1.3902.6053.19.1.3.11.1.30724.51
    trapSATASASBUSTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 51}

-- 1.3.6.1.4.1.3902.6053.19.1.3.11.1.30724.52
    trapProcessorFrontSideBUSTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 52}

-- 1.3.6.1.4.1.3902.6053.19.1.3.11.1.30724.53
    trapRealTimeClockTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 53}

-- 1.3.6.1.4.1.3902.6053.19.1.3.11.1.30724.54
    trapSystemFirmwareTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 54}

-- 1.3.6.1.4.1.3902.6053.19.1.3.11.1.30724.160
    trapMainBoardTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 160}

-- 1.3.6.1.4.1.3902.6053.19.1.3.11.1.30724.208
    trapNetPortTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 208}

-- 1.3.6.1.4.1.3902.6053.19.1.3.11.1.30724.209
    trapLogicalDiskTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 209}

-- 1.3.6.1.4.1.3902.6053.19.1.3.11.1.30724.210
    trapStorageCTRLTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 210}

-- 1.3.6.1.4.1.3902.6053.19.1.3.11.1.30724.272
    trapNICSFPTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 272}

-- 1.3.6.1.4.1.3902.6053.19.1.3.11.1.30724.273
    trapOCPSFPTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 273}

-- 1.3.6.1.4.1.3902.6053.19.1.3.11.1.30724.275
    trapSNICSFPTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 28}

-- 1.3.6.1.4.1.3902.6053.19.1.3.11.1.30724.277
    trapDPUT100TemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 277}

-- 1.3.6.1.4.1.3902.6053.19.1.3.11.1.30724.278
    trapDPUT200TemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 278}

-- 1.3.6.1.4.1.3902.6053.19.1.3.11.1.30724.279
    trapBSC25GTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 279}

-- 1.3.6.1.4.1.3902.6053.19.1.3.11.1.30724.281
    trapNEOTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 281}

-- 1.3.6.1.4.1.3902.6053.19.1.3.11.1.30724.282
    trapZiJinTemperatureIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30724-ucFruId, trap-30724-aucCurrentValue, trap-30724-aucThresholdValue, trap-30724-aucUnitStr, trap-30724-aucSensorName, acTrapTime, acTrapEventSubject, acTrapSeverity, acTrapDescription, acTrapProductSerial, acTrapState, acTrapDeviceSN, acTrapAddInform, dwTrapIndex
		                                        }
		STATUS			current
		DESCRIPTION		"Temperature is lower than lower-non-recoverable threshold."
		::=  {  trap-30724-reasoninfo 282}

-- 1.3.6.1.4.1.3902.6053.19.1.3.11.1.30725
    trap-30725-addinfo OBJECT IDENTIFIER ::= {trap-addinfo 30725}

-- 1.3.6.1.4.1.3902.6053.19.1.3.11.2.30725.1
    trap-30725-ucFruId OBJECT-TYPE
        SYNTAX Unsigned32
        ACCESS accessible-for-notify
        STATUS current
        DESCRIPTION 
            "FRU ID"
        ::= {trap-30725-addinfo 1}

-- 1.3.6.1.4.1.3902.6053.19.1.3.11.2.30725.5
    trap-30725-aucCurrentValue OBJECT-TYPE
        SYNTAX DisplayString
        ACCESS accessible-for-notify
        STATUS current
        DESCRIPTION 
            "Current value"
        ::= {trap-30725-addinfo 5}

-- 1.3.6.1.4.1.3902.6053.19.1.3.11.2.30725.6
    trap-30725-aucThresholdValue OBJECT-TYPE
        SYNTAX DisplayString
        ACCESS accessible-for-notify
        STATUS current
        DESCRIPTION 
            "Threshold value"
        ::= {trap-30725-addinfo 6}

-- 1.3.6.1.4.1.3902.6053.19.1.3.11.2.30725.7
    trap-30725-aucUnitStr OBJECT-TYPE
        SYNTAX DisplayString
        ACCESS accessible-for-notify
        STATUS current
        DESCRIPTION 
            "Unit"
        ::= {trap-30725-addinfo 7}

-- 1.3.6.1.4.1.3902.6053.19.1.3.11.2.30725.8
    trap-30725-aucSensorName OBJECT-TYPE
        SYNTAX DisplayString
        ACCESS accessible-for-notify
        STATUS current
        DESCRIPTION 
            "Sensor name"
        ::= {trap-30725-addinfo 8}

-- 1.3.6.1.4.1.3902.6053.19.1.3.11.1.30725
    trapTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-alarm 30725}

-- 1.3.6.1.4.1.3902.6053.19.1.3.11.1.30725
    trap-30725-reasoninfo OBJECT IDENTIFIER ::= {trap-alarm 30725}

-- 1.3.6.1.4.1.3902.6053.19.1.3.11.1.30725.0
    trapUnspecifiedTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 0}

-- 1.3.6.1.4.1.3902.6053.19.1.3.11.1.30725.1
    trapOtherTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 1}

-- 1.3.6.1.4.1.3902.6053.19.1.3.11.1.30725.2
    trapUnkownTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 2}

-- 1.3.6.1.4.1.3902.6053.19.1.3.11.1.30725.3
    trapProcessorTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 3}

-- 1.3.6.1.4.1.3902.6053.19.1.3.11.1.30725.4
    trapDiskTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 4}

-- 1.3.6.1.4.1.3902.6053.19.1.3.11.1.30725.5
    trapPeripheralTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 5}

-- 1.3.6.1.4.1.3902.6053.19.1.3.11.1.30725.6
    trapSystemManagementModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 6}

-- 1.3.6.1.4.1.3902.6053.19.1.3.11.1.30725.7
    trapSystemBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 7}

-- 1.3.6.1.4.1.3902.6053.19.1.3.11.1.30725.8
    trapMemoryTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 8}

-- 1.3.6.1.4.1.3902.6053.19.1.3.11.1.30725.9
    trapProcessorModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 9}

-- 1.3.6.1.4.1.3902.6053.19.1.3.11.1.30725.10
    trapPowerSupplyTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 10}

-- 1.3.6.1.4.1.3902.6053.19.1.3.11.1.30725.11
    trapADDINCardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 11}

-- 1.3.6.1.4.1.3902.6053.19.1.3.11.1.30725.12
    trapFrontPanelBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 12}

-- 1.3.6.1.4.1.3902.6053.19.1.3.11.1.30725.13
    trapBackPanelBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 13}

-- 1.3.6.1.4.1.3902.6053.19.1.3.11.1.30725.14
    trapPowerSystemBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 14}

-- 1.3.6.1.4.1.3902.6053.19.1.3.11.1.30725.15
    trapDriveBackplaneTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 15}

-- 1.3.6.1.4.1.3902.6053.19.1.3.11.1.30725.16
    trapSystemInternalExpansionBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 16}

-- 1.3.6.1.4.1.3902.6053.19.1.3.11.1.30725.17
    trapOtherSystemBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 17}

-- 1.3.6.1.4.1.3902.6053.19.1.3.11.1.30725.18
    trapProcessorBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 18}

-- 1.3.6.1.4.1.3902.6053.19.1.3.11.1.30725.19
    trapPowerUnitTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 19}

-- 1.3.6.1.4.1.3902.6053.19.1.3.11.1.30725.20
    trapPowerModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 20}

-- 1.3.6.1.4.1.3902.6053.19.1.3.11.1.30725.21
    trapPowerManagementBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 21}

-- 1.3.6.1.4.1.3902.6053.19.1.3.11.1.30725.22
    trapChassisBackPanelBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 22}

-- 1.3.6.1.4.1.3902.6053.19.1.3.11.1.30725.23
    trapSystemChassisTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 23}

-- 1.3.6.1.4.1.3902.6053.19.1.3.11.1.30725.24
    trapSUBChassisTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 24}

-- 1.3.6.1.4.1.3902.6053.19.1.3.11.1.30725.25
    trapOtherChassisBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 25}

-- 1.3.6.1.4.1.3902.6053.19.1.3.11.1.30725.26
    trapDiskDriveTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 26}

-- 1.3.6.1.4.1.3902.6053.19.1.3.11.1.30725.27
    trapPeripheralBayTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 27}

-- 1.3.6.1.4.1.3902.6053.19.1.3.11.1.30725.28
    trapDeviceBayTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 28}

-- 1.3.6.1.4.1.3902.6053.19.1.3.11.1.30725.29
    trapFanCoolingTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 29}

-- 1.3.6.1.4.1.3902.6053.19.1.3.11.1.30725.30
    trapCoolingUnitTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 30}

-- 1.3.6.1.4.1.3902.6053.19.1.3.11.1.30725.31
    trapCableInterconnectTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 31}

-- 1.3.6.1.4.1.3902.6053.19.1.3.11.1.30725.32
    trapMemoryDeviceTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 32}

-- 1.3.6.1.4.1.3902.6053.19.1.3.11.1.30725.33
    trapSystemManagementSoftwareTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 33}

-- 1.3.6.1.4.1.3902.6053.19.1.3.11.1.30725.34
    trapBiosTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 34}

-- 1.3.6.1.4.1.3902.6053.19.1.3.11.1.30725.35
    trapOperatingSystemTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 35}

-- 1.3.6.1.4.1.3902.6053.19.1.3.11.1.30725.36
    trapSystemBusTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 36}

-- 1.3.6.1.4.1.3902.6053.19.1.3.11.1.30725.37
    trapGroupTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 37}

-- 1.3.6.1.4.1.3902.6053.19.1.3.11.1.30725.38
    trapRemotManagementDeviceTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 38}

-- 1.3.6.1.4.1.3902.6053.19.1.3.11.1.30725.39
    trapExternalEnvironmentTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 39}

-- 1.3.6.1.4.1.3902.6053.19.1.3.11.1.30725.40
    trapBatteryTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 40}

-- 1.3.6.1.4.1.3902.6053.19.1.3.11.1.30725.41
    trapProcessBladeModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 41}

-- 1.3.6.1.4.1.3902.6053.19.1.3.11.1.30725.42
    trapConnectivitySwitchTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 42}

-- 1.3.6.1.4.1.3902.6053.19.1.3.11.1.30725.43
    trapProcessorMemoryModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 43}

-- 1.3.6.1.4.1.3902.6053.19.1.3.11.1.30725.44
    trapIOModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 44}

-- 1.3.6.1.4.1.3902.6053.19.1.3.11.1.30725.45
    trapProcessorIOModuleTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 45}

-- 1.3.6.1.4.1.3902.6053.19.1.3.11.1.30725.46
    trapMGMTControllerFirmwareTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 46}

-- 1.3.6.1.4.1.3902.6053.19.1.3.11.1.30725.47
    trapIPMIChannelTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 47}

-- 1.3.6.1.4.1.3902.6053.19.1.3.11.1.30725.48
    trapPCIBUSTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 48}

-- 1.3.6.1.4.1.3902.6053.19.1.3.11.1.30725.49
    trapPCIExpressBUSTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 49}

-- 1.3.6.1.4.1.3902.6053.19.1.3.11.1.30725.50
    trapSCSIBUSTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 50}

-- 1.3.6.1.4.1.3902.6053.19.1.3.11.1.30725.51
    trapSATASASBUSTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 51}

-- 1.3.6.1.4.1.3902.6053.19.1.3.11.1.30725.52
    trapProcessorFrontSideBUSTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 52}

-- 1.3.6.1.4.1.3902.6053.19.1.3.11.1.30725.53
    trapRealTimeClockTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 53}

-- 1.3.6.1.4.1.3902.6053.19.1.3.11.1.30725.54
    trapSystemFirmwareTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 54}

-- 1.3.6.1.4.1.3902.6053.19.1.3.11.1.30725.160
    trapMainBoardTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 160}

-- 1.3.6.1.4.1.3902.6053.19.1.3.11.1.30725.208
    trapNetPortTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 208}

-- 1.3.6.1.4.1.3902.6053.19.1.3.11.1.30725.209
    trapLogicalDiskTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 209}

-- 1.3.6.1.4.1.3902.6053.19.1.3.11.1.30725.210
    trapStorageCTRLTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 210}

-- 1.3.6.1.4.1.3902.6053.19.1.3.11.1.30725.272
    trapNICSFPTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 272}

-- 1.3.6.1.4.1.3902.6053.19.1.3.11.1.30725.273
    trapOCPSFPTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 273}

-- 1.3.6.1.4.1.3902.6053.19.1.3.11.1.30725.275
    trapSNICSFPTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 28}

-- 1.3.6.1.4.1.3902.6053.19.1.3.11.1.30725.277
    trapDPUT100TemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 277}

-- 1.3.6.1.4.1.3902.6053.19.1.3.11.1.30725.278
    trapDPUT200TemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 278}

-- 1.3.6.1.4.1.3902.6053.19.1.3.11.1.30725.279
    trapBSC25GTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 279}

-- 1.3.6.1.4.1.3902.6053.19.1.3.11.1.30725.281
    trapNEOTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 281}

-- 1.3.6.1.4.1.3902.6053.19.1.3.11.1.30725.282
    trapZiJinTemperatureIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30725-ucFruId, trap-30725-aucCurrentValue, trap-30725-aucThresholdValue, trap-30725-aucUnitStr, trap-30725-aucSensorName, acTrapTime, acTrapEventSubject, acTrapSeverity, acTrapDescription, acTrapProductSerial, acTrapState, acTrapDeviceSN, acTrapAddInform, dwTrapIndex
		                                        }
		STATUS			current
		DESCRIPTION		"Temperature is higher than upper-critical threshold."
		::=  {  trap-30725-reasoninfo 282}

-- 1.3.6.1.4.1.3902.6053.19.1.3.11.1.30726
    trap-30726-addinfo OBJECT IDENTIFIER ::= {trap-addinfo 30726}

-- 1.3.6.1.4.1.3902.6053.19.1.3.11.2.30726.1
    trap-30726-ucFruId OBJECT-TYPE
        SYNTAX Unsigned32
        ACCESS accessible-for-notify
        STATUS current
        DESCRIPTION 
            "FRU ID"
        ::= {trap-30726-addinfo 1}

-- 1.3.6.1.4.1.3902.6053.19.1.3.11.2.30726.5
    trap-30726-aucCurrentValue OBJECT-TYPE
        SYNTAX DisplayString
        ACCESS accessible-for-notify
        STATUS current
        DESCRIPTION 
            "Current value"
        ::= {trap-30726-addinfo 5}

-- 1.3.6.1.4.1.3902.6053.19.1.3.11.2.30726.6
    trap-30726-aucThresholdValue OBJECT-TYPE
        SYNTAX DisplayString
        ACCESS accessible-for-notify
        STATUS current
        DESCRIPTION 
            "Threshold value"
        ::= {trap-30726-addinfo 6}

-- 1.3.6.1.4.1.3902.6053.19.1.3.11.2.30726.7
    trap-30726-aucUnitStr OBJECT-TYPE
        SYNTAX DisplayString
        ACCESS accessible-for-notify
        STATUS current
        DESCRIPTION 
            "Unit"
        ::= {trap-30726-addinfo 7}

-- 1.3.6.1.4.1.3902.6053.19.1.3.11.2.30726.8
    trap-30726-aucSensorName OBJECT-TYPE
        SYNTAX DisplayString
        ACCESS accessible-for-notify
        STATUS current
        DESCRIPTION 
            "Sensor name"
        ::= {trap-30726-addinfo 8}

-- 1.3.6.1.4.1.3902.6053.19.1.3.11.1.30726
    trapTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-alarm 30726}

-- 1.3.6.1.4.1.3902.6053.19.1.3.11.1.30726
    trap-30726-reasoninfo OBJECT IDENTIFIER ::= {trap-alarm 30726}

-- 1.3.6.1.4.1.3902.6053.19.1.3.11.1.30726.0
    trapUnspecifiedTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 0}

-- 1.3.6.1.4.1.3902.6053.19.1.3.11.1.30726.1
    trapOtherTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 1}

-- 1.3.6.1.4.1.3902.6053.19.1.3.11.1.30726.2
    trapUnkownTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 2}

-- 1.3.6.1.4.1.3902.6053.19.1.3.11.1.30726.3
    trapProcessorTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 3}

-- 1.3.6.1.4.1.3902.6053.19.1.3.11.1.30726.4
    trapDiskTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 4}

-- 1.3.6.1.4.1.3902.6053.19.1.3.11.1.30726.5
    trapPeripheralTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 5}

-- 1.3.6.1.4.1.3902.6053.19.1.3.11.1.30726.6
    trapSystemManagementModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 6}

-- 1.3.6.1.4.1.3902.6053.19.1.3.11.1.30726.7
    trapSystemBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 7}

-- 1.3.6.1.4.1.3902.6053.19.1.3.11.1.30726.8
    trapMemoryTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 8}

-- 1.3.6.1.4.1.3902.6053.19.1.3.11.1.30726.9
    trapProcessorModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 9}

-- 1.3.6.1.4.1.3902.6053.19.1.3.11.1.30726.10
    trapPowerSupplyTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 10}

-- 1.3.6.1.4.1.3902.6053.19.1.3.11.1.30726.11
    trapADDINCardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 11}

-- 1.3.6.1.4.1.3902.6053.19.1.3.11.1.30726.12
    trapFrontPanelBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 12}

-- 1.3.6.1.4.1.3902.6053.19.1.3.11.1.30726.13
    trapBackPanelBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 13}

-- 1.3.6.1.4.1.3902.6053.19.1.3.11.1.30726.14
    trapPowerSystemBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 14}

-- 1.3.6.1.4.1.3902.6053.19.1.3.11.1.30726.15
    trapDriveBackplaneTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 15}

-- 1.3.6.1.4.1.3902.6053.19.1.3.11.1.30726.16
    trapSystemInternalExpansionBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 16}

-- 1.3.6.1.4.1.3902.6053.19.1.3.11.1.30726.17
    trapOtherSystemBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 17}

-- 1.3.6.1.4.1.3902.6053.19.1.3.11.1.30726.18
    trapProcessorBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 18}

-- 1.3.6.1.4.1.3902.6053.19.1.3.11.1.30726.19
    trapPowerUnitTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 19}

-- 1.3.6.1.4.1.3902.6053.19.1.3.11.1.30726.20
    trapPowerModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 20}

-- 1.3.6.1.4.1.3902.6053.19.1.3.11.1.30726.21
    trapPowerManagementBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 21}

-- 1.3.6.1.4.1.3902.6053.19.1.3.11.1.30726.22
    trapChassisBackPanelBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 22}

-- 1.3.6.1.4.1.3902.6053.19.1.3.11.1.30726.23
    trapSystemChassisTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 23}

-- 1.3.6.1.4.1.3902.6053.19.1.3.11.1.30726.24
    trapSUBChassisTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 24}

-- 1.3.6.1.4.1.3902.6053.19.1.3.11.1.30726.25
    trapOtherChassisBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 25}

-- 1.3.6.1.4.1.3902.6053.19.1.3.11.1.30726.26
    trapDiskDriveTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 26}

-- 1.3.6.1.4.1.3902.6053.19.1.3.11.1.30726.27
    trapPeripheralBayTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 27}

-- 1.3.6.1.4.1.3902.6053.19.1.3.11.1.30726.28
    trapDeviceBayTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 28}

-- 1.3.6.1.4.1.3902.6053.19.1.3.11.1.30726.29
    trapFanCoolingTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 29}

-- 1.3.6.1.4.1.3902.6053.19.1.3.11.1.30726.30
    trapCoolingUnitTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 30}

-- 1.3.6.1.4.1.3902.6053.19.1.3.11.1.30726.31
    trapCableInterconnectTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 31}

-- 1.3.6.1.4.1.3902.6053.19.1.3.11.1.30726.32
    trapMemoryDeviceTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 32}

-- 1.3.6.1.4.1.3902.6053.19.1.3.11.1.30726.33
    trapSystemManagementSoftwareTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 33}

-- 1.3.6.1.4.1.3902.6053.19.1.3.11.1.30726.34
    trapBiosTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 34}

-- 1.3.6.1.4.1.3902.6053.19.1.3.11.1.30726.35
    trapOperatingSystemTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 35}

-- 1.3.6.1.4.1.3902.6053.19.1.3.11.1.30726.36
    trapSystemBusTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 36}

-- 1.3.6.1.4.1.3902.6053.19.1.3.11.1.30726.37
    trapGroupTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 37}

-- 1.3.6.1.4.1.3902.6053.19.1.3.11.1.30726.38
    trapRemotManagementDeviceTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 38}

-- 1.3.6.1.4.1.3902.6053.19.1.3.11.1.30726.39
    trapExternalEnvironmentTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 39}

-- 1.3.6.1.4.1.3902.6053.19.1.3.11.1.30726.40
    trapBatteryTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 40}

-- 1.3.6.1.4.1.3902.6053.19.1.3.11.1.30726.41
    trapProcessBladeModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 41}

-- 1.3.6.1.4.1.3902.6053.19.1.3.11.1.30726.42
    trapConnectivitySwitchTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 42}

-- 1.3.6.1.4.1.3902.6053.19.1.3.11.1.30726.43
    trapProcessorMemoryModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 43}

-- 1.3.6.1.4.1.3902.6053.19.1.3.11.1.30726.44
    trapIOModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 44}

-- 1.3.6.1.4.1.3902.6053.19.1.3.11.1.30726.45
    trapProcessorIOModuleTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 45}

-- 1.3.6.1.4.1.3902.6053.19.1.3.11.1.30726.46
    trapMGMTControllerFirmwareTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 46}

-- 1.3.6.1.4.1.3902.6053.19.1.3.11.1.30726.47
    trapIPMIChannelTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 47}

-- 1.3.6.1.4.1.3902.6053.19.1.3.11.1.30726.48
    trapPCIBUSTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 48}

-- 1.3.6.1.4.1.3902.6053.19.1.3.11.1.30726.49
    trapPCIExpressBUSTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 49}

-- 1.3.6.1.4.1.3902.6053.19.1.3.11.1.30726.50
    trapSCSIBUSTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 50}

-- 1.3.6.1.4.1.3902.6053.19.1.3.11.1.30726.51
    trapSATASASBUSTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 51}

-- 1.3.6.1.4.1.3902.6053.19.1.3.11.1.30726.52
    trapProcessorFrontSideBUSTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 52}

-- 1.3.6.1.4.1.3902.6053.19.1.3.11.1.30726.53
    trapRealTimeClockTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 53}

-- 1.3.6.1.4.1.3902.6053.19.1.3.11.1.30726.54
    trapSystemFirmwareTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 54}

-- 1.3.6.1.4.1.3902.6053.19.1.3.11.1.30726.160
    trapMainBoardTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 160}

-- 1.3.6.1.4.1.3902.6053.19.1.3.11.1.30726.208
    trapNetPortTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 208}

-- 1.3.6.1.4.1.3902.6053.19.1.3.11.1.30726.209
    trapLogicalDiskTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 209}

-- 1.3.6.1.4.1.3902.6053.19.1.3.11.1.30726.210
    trapStorageCTRLTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 210}

-- 1.3.6.1.4.1.3902.6053.19.1.3.11.1.30726.272
    trapNICSFPTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 272}

-- 1.3.6.1.4.1.3902.6053.19.1.3.11.1.30726.273
    trapOCPSFPTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 273}

-- 1.3.6.1.4.1.3902.6053.19.1.3.11.1.30726.275
    trapSNICSFPTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 28}

-- 1.3.6.1.4.1.3902.6053.19.1.3.11.1.30726.277
    trapDPUT100TemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 277}

-- 1.3.6.1.4.1.3902.6053.19.1.3.11.1.30726.278
    trapDPUT200TemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 278}

-- 1.3.6.1.4.1.3902.6053.19.1.3.11.1.30726.279
    trapBSC25GTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 279}

-- 1.3.6.1.4.1.3902.6053.19.1.3.11.1.30726.281
    trapNEOTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 281}

-- 1.3.6.1.4.1.3902.6053.19.1.3.11.1.30726.282
    trapZiJinTemperatureIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30726-ucFruId, trap-30726-aucCurrentValue, trap-30726-aucThresholdValue, trap-30726-aucUnitStr, trap-30726-aucSensorName, acTrapTime, acTrapEventSubject, acTrapSeverity, acTrapDescription, acTrapProductSerial, acTrapState, acTrapDeviceSN, acTrapAddInform, dwTrapIndex
		                                        }
		STATUS			current
		DESCRIPTION		"Temperature is higher than upper-non-recoverable threshold."
		::=  {  trap-30726-reasoninfo 282}

-- 1.3.6.1.4.1.3902.6053.19.1.3.11.1.30727
    trap-30727-addinfo OBJECT IDENTIFIER ::= {trap-addinfo 30727}

-- 1.3.6.1.4.1.3902.6053.19.1.3.11.2.30727.1
    trap-30727-ucFruId OBJECT-TYPE
        SYNTAX Unsigned32
        ACCESS accessible-for-notify
        STATUS current
        DESCRIPTION 
            "FRU ID"
        ::= {trap-30727-addinfo 1}

-- 1.3.6.1.4.1.3902.6053.19.1.3.11.2.30727.5
    trap-30727-aucCurrentValue OBJECT-TYPE
        SYNTAX DisplayString
        ACCESS accessible-for-notify
        STATUS current
        DESCRIPTION 
            "Current value"
        ::= {trap-30727-addinfo 5}

-- 1.3.6.1.4.1.3902.6053.19.1.3.11.2.30727.6
    trap-30727-aucThresholdValue OBJECT-TYPE
        SYNTAX DisplayString
        ACCESS accessible-for-notify
        STATUS current
        DESCRIPTION 
            "Threshold value"
        ::= {trap-30727-addinfo 6}

-- 1.3.6.1.4.1.3902.6053.19.1.3.11.2.30727.7
    trap-30727-aucUnitStr OBJECT-TYPE
        SYNTAX DisplayString
        ACCESS accessible-for-notify
        STATUS current
        DESCRIPTION 
            "Unit"
        ::= {trap-30727-addinfo 7}

-- 1.3.6.1.4.1.3902.6053.19.1.3.11.2.30727.8
    trap-30727-aucSensorName OBJECT-TYPE
        SYNTAX DisplayString
        ACCESS accessible-for-notify
        STATUS current
        DESCRIPTION 
            "Sensor name"
        ::= {trap-30727-addinfo 8}

-- 1.3.6.1.4.1.3902.6053.19.1.3.11.1.30727
    trapVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-alarm 30727}

-- 1.3.6.1.4.1.3902.6053.19.1.3.11.1.30727
    trap-30727-reasoninfo OBJECT IDENTIFIER ::= {trap-alarm 30727}

-- 1.3.6.1.4.1.3902.6053.19.1.3.11.1.30727.0
    trapUnspecifiedVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 0}

-- 1.3.6.1.4.1.3902.6053.19.1.3.11.1.30727.1
    trapOtherVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 1}

-- 1.3.6.1.4.1.3902.6053.19.1.3.11.1.30727.2
    trapUnkownVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 2}

-- 1.3.6.1.4.1.3902.6053.19.1.3.11.1.30727.3
    trapProcessorVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 3}

-- 1.3.6.1.4.1.3902.6053.19.1.3.11.1.30727.4
    trapDiskVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 4}

-- 1.3.6.1.4.1.3902.6053.19.1.3.11.1.30727.5
    trapPeripheralVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 5}

-- 1.3.6.1.4.1.3902.6053.19.1.3.11.1.30727.6
    trapSystemManagementModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 6}

-- 1.3.6.1.4.1.3902.6053.19.1.3.11.1.30727.7
    trapSystemBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 7}

-- 1.3.6.1.4.1.3902.6053.19.1.3.11.1.30727.8
    trapMemoryVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 8}

-- 1.3.6.1.4.1.3902.6053.19.1.3.11.1.30727.9
    trapProcessorModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 9}

-- 1.3.6.1.4.1.3902.6053.19.1.3.11.1.30727.10
    trapPowerSupplyVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 10}

-- 1.3.6.1.4.1.3902.6053.19.1.3.11.1.30727.11
    trapADDINCardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 11}

-- 1.3.6.1.4.1.3902.6053.19.1.3.11.1.30727.12
    trapFrontPanelBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 12}

-- 1.3.6.1.4.1.3902.6053.19.1.3.11.1.30727.13
    trapBackPanelBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 13}

-- 1.3.6.1.4.1.3902.6053.19.1.3.11.1.30727.14
    trapPowerSystemBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 14}

-- 1.3.6.1.4.1.3902.6053.19.1.3.11.1.30727.15
    trapDriveBackplaneVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 15}

-- 1.3.6.1.4.1.3902.6053.19.1.3.11.1.30727.16
    trapSystemInternalExpansionBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 16}

-- 1.3.6.1.4.1.3902.6053.19.1.3.11.1.30727.17
    trapOtherSystemBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 17}

-- 1.3.6.1.4.1.3902.6053.19.1.3.11.1.30727.18
    trapProcessorBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 18}

-- 1.3.6.1.4.1.3902.6053.19.1.3.11.1.30727.19
    trapPowerUnitVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 19}

-- 1.3.6.1.4.1.3902.6053.19.1.3.11.1.30727.20
    trapPowerModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 20}

-- 1.3.6.1.4.1.3902.6053.19.1.3.11.1.30727.21
    trapPowerManagementBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 21}

-- 1.3.6.1.4.1.3902.6053.19.1.3.11.1.30727.22
    trapChassisBackPanelBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 22}

-- 1.3.6.1.4.1.3902.6053.19.1.3.11.1.30727.23
    trapSystemChassisVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 23}

-- 1.3.6.1.4.1.3902.6053.19.1.3.11.1.30727.24
    trapSUBChassisVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 24}

-- 1.3.6.1.4.1.3902.6053.19.1.3.11.1.30727.25
    trapOtherChassisBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 25}

-- 1.3.6.1.4.1.3902.6053.19.1.3.11.1.30727.26
    trapDiskDriveVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 26}

-- 1.3.6.1.4.1.3902.6053.19.1.3.11.1.30727.27
    trapPeripheralBayVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 27}

-- 1.3.6.1.4.1.3902.6053.19.1.3.11.1.30727.28
    trapDeviceBayVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 28}

-- 1.3.6.1.4.1.3902.6053.19.1.3.11.1.30727.29
    trapFanCoolingVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 29}

-- 1.3.6.1.4.1.3902.6053.19.1.3.11.1.30727.30
    trapCoolingUnitVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 30}

-- 1.3.6.1.4.1.3902.6053.19.1.3.11.1.30727.31
    trapCableInterconnectVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 31}

-- 1.3.6.1.4.1.3902.6053.19.1.3.11.1.30727.32
    trapMemoryDeviceVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 32}

-- 1.3.6.1.4.1.3902.6053.19.1.3.11.1.30727.33
    trapSystemManagementSoftwareVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 33}

-- 1.3.6.1.4.1.3902.6053.19.1.3.11.1.30727.34
    trapBiosVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 34}

-- 1.3.6.1.4.1.3902.6053.19.1.3.11.1.30727.35
    trapOperatingSystemVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 35}

-- 1.3.6.1.4.1.3902.6053.19.1.3.11.1.30727.36
    trapSystemBusVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 36}

-- 1.3.6.1.4.1.3902.6053.19.1.3.11.1.30727.37
    trapGroupVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 37}

-- 1.3.6.1.4.1.3902.6053.19.1.3.11.1.30727.38
    trapRemotManagementDeviceVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 38}

-- 1.3.6.1.4.1.3902.6053.19.1.3.11.1.30727.39
    trapExternalEnvironmentVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 39}

-- 1.3.6.1.4.1.3902.6053.19.1.3.11.1.30727.40
    trapBatteryVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 40}

-- 1.3.6.1.4.1.3902.6053.19.1.3.11.1.30727.41
    trapProcessBladeModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 41}

-- 1.3.6.1.4.1.3902.6053.19.1.3.11.1.30727.42
    trapConnectivitySwitchVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 42}

-- 1.3.6.1.4.1.3902.6053.19.1.3.11.1.30727.43
    trapProcessorMemoryModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 43}

-- 1.3.6.1.4.1.3902.6053.19.1.3.11.1.30727.44
    trapIOModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 44}

-- 1.3.6.1.4.1.3902.6053.19.1.3.11.1.30727.45
    trapProcessorIOModuleVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 45}

-- 1.3.6.1.4.1.3902.6053.19.1.3.11.1.30727.46
    trapMGMTControllerFirmwareVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 46}

-- 1.3.6.1.4.1.3902.6053.19.1.3.11.1.30727.47
    trapIPMIChannelVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 47}

-- 1.3.6.1.4.1.3902.6053.19.1.3.11.1.30727.48
    trapPCIBUSVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 48}

-- 1.3.6.1.4.1.3902.6053.19.1.3.11.1.30727.49
    trapPCIExpressBUSVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 49}

-- 1.3.6.1.4.1.3902.6053.19.1.3.11.1.30727.50
    trapSCSIBUSVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 50}

-- 1.3.6.1.4.1.3902.6053.19.1.3.11.1.30727.51
    trapSATASASBUSVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 51}

-- 1.3.6.1.4.1.3902.6053.19.1.3.11.1.30727.52
    trapProcessorFrontSideBUSVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 52}

-- 1.3.6.1.4.1.3902.6053.19.1.3.11.1.30727.53
    trapRealTimeClockVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 53}

-- 1.3.6.1.4.1.3902.6053.19.1.3.11.1.30727.54
    trapSystemFirmwareVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 54}

-- 1.3.6.1.4.1.3902.6053.19.1.3.11.1.30727.160
    trapMainBoardVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 160}

-- 1.3.6.1.4.1.3902.6053.19.1.3.11.1.30727.208
    trapNetPortVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 208}

-- 1.3.6.1.4.1.3902.6053.19.1.3.11.1.30727.209
    trapLogicalDiskVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 209}

-- 1.3.6.1.4.1.3902.6053.19.1.3.11.1.30727.210
    trapStorageCTRLVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 210}

-- 1.3.6.1.4.1.3902.6053.19.1.3.11.1.30727.272
    trapNICSFPVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 272}

-- 1.3.6.1.4.1.3902.6053.19.1.3.11.1.30727.273
    trapOCPSFPVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 273}

-- 1.3.6.1.4.1.3902.6053.19.1.3.11.1.30727.275
    trapSNICSFPVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 28}

-- 1.3.6.1.4.1.3902.6053.19.1.3.11.1.30727.277
    trapDPUT100VoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 277}

-- 1.3.6.1.4.1.3902.6053.19.1.3.11.1.30727.278
    trapDPUT200VoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 278}

-- 1.3.6.1.4.1.3902.6053.19.1.3.11.1.30727.279
    trapBSC25GVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 279}

-- 1.3.6.1.4.1.3902.6053.19.1.3.11.1.30727.281
    trapNEOVoltageIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30727-ucFruId, trap-30727-aucCurrentValue, trap-30727-aucThresholdValue, trap-30727-aucUnitStr, trap-30727-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-critical threshold."
		::=  {  trap-30727-reasoninfo 281}

-- 1.3.6.1.4.1.3902.6053.19.1.3.11.1.30728
    trap-30728-addinfo OBJECT IDENTIFIER ::= {trap-addinfo 30728}

-- 1.3.6.1.4.1.3902.6053.19.1.3.11.2.30728.1
    trap-30728-ucFruId OBJECT-TYPE
        SYNTAX Unsigned32
        ACCESS accessible-for-notify
        STATUS current
        DESCRIPTION 
            "FRU ID"
        ::= {trap-30728-addinfo 1}

-- 1.3.6.1.4.1.3902.6053.19.1.3.11.2.30728.5
    trap-30728-aucCurrentValue OBJECT-TYPE
        SYNTAX DisplayString
        ACCESS accessible-for-notify
        STATUS current
        DESCRIPTION 
            "Current value"
        ::= {trap-30728-addinfo 5}

-- 1.3.6.1.4.1.3902.6053.19.1.3.11.2.30728.6
    trap-30728-aucThresholdValue OBJECT-TYPE
        SYNTAX DisplayString
        ACCESS accessible-for-notify
        STATUS current
        DESCRIPTION 
            "Threshold value"
        ::= {trap-30728-addinfo 6}

-- 1.3.6.1.4.1.3902.6053.19.1.3.11.2.30728.7
    trap-30728-aucUnitStr OBJECT-TYPE
        SYNTAX DisplayString
        ACCESS accessible-for-notify
        STATUS current
        DESCRIPTION 
            "Unit"
        ::= {trap-30728-addinfo 7}

-- 1.3.6.1.4.1.3902.6053.19.1.3.11.2.30728.8
    trap-30728-aucSensorName OBJECT-TYPE
        SYNTAX DisplayString
        ACCESS accessible-for-notify
        STATUS current
        DESCRIPTION 
            "Sensor name"
        ::= {trap-30728-addinfo 8}

-- 1.3.6.1.4.1.3902.6053.19.1.3.11.1.30728
    trapVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-alarm 30728}

-- 1.3.6.1.4.1.3902.6053.19.1.3.11.1.30728
    trap-30728-reasoninfo OBJECT IDENTIFIER ::= {trap-alarm 30728}

-- 1.3.6.1.4.1.3902.6053.19.1.3.11.1.30728.0
    trapUnspecifiedVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 0}

-- 1.3.6.1.4.1.3902.6053.19.1.3.11.1.30728.1
    trapOtherVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 1}

-- 1.3.6.1.4.1.3902.6053.19.1.3.11.1.30728.2
    trapUnkownVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 2}

-- 1.3.6.1.4.1.3902.6053.19.1.3.11.1.30728.3
    trapProcessorVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 3}

-- 1.3.6.1.4.1.3902.6053.19.1.3.11.1.30728.4
    trapDiskVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 4}

-- 1.3.6.1.4.1.3902.6053.19.1.3.11.1.30728.5
    trapPeripheralVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 5}

-- 1.3.6.1.4.1.3902.6053.19.1.3.11.1.30728.6
    trapSystemManagementModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 6}

-- 1.3.6.1.4.1.3902.6053.19.1.3.11.1.30728.7
    trapSystemBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 7}

-- 1.3.6.1.4.1.3902.6053.19.1.3.11.1.30728.8
    trapMemoryVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 8}

-- 1.3.6.1.4.1.3902.6053.19.1.3.11.1.30728.9
    trapProcessorModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 9}

-- 1.3.6.1.4.1.3902.6053.19.1.3.11.1.30728.10
    trapPowerSupplyVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 10}

-- 1.3.6.1.4.1.3902.6053.19.1.3.11.1.30728.11
    trapADDINCardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 11}

-- 1.3.6.1.4.1.3902.6053.19.1.3.11.1.30728.12
    trapFrontPanelBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 12}

-- 1.3.6.1.4.1.3902.6053.19.1.3.11.1.30728.13
    trapBackPanelBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 13}

-- 1.3.6.1.4.1.3902.6053.19.1.3.11.1.30728.14
    trapPowerSystemBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 14}

-- 1.3.6.1.4.1.3902.6053.19.1.3.11.1.30728.15
    trapDriveBackplaneVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 15}

-- 1.3.6.1.4.1.3902.6053.19.1.3.11.1.30728.16
    trapSystemInternalExpansionBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 16}

-- 1.3.6.1.4.1.3902.6053.19.1.3.11.1.30728.17
    trapOtherSystemBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 17}

-- 1.3.6.1.4.1.3902.6053.19.1.3.11.1.30728.18
    trapProcessorBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 18}

-- 1.3.6.1.4.1.3902.6053.19.1.3.11.1.30728.19
    trapPowerUnitVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 19}

-- 1.3.6.1.4.1.3902.6053.19.1.3.11.1.30728.20
    trapPowerModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 20}

-- 1.3.6.1.4.1.3902.6053.19.1.3.11.1.30728.21
    trapPowerManagementBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 21}

-- 1.3.6.1.4.1.3902.6053.19.1.3.11.1.30728.22
    trapChassisBackPanelBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 22}

-- 1.3.6.1.4.1.3902.6053.19.1.3.11.1.30728.23
    trapSystemChassisVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 23}

-- 1.3.6.1.4.1.3902.6053.19.1.3.11.1.30728.24
    trapSUBChassisVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 24}

-- 1.3.6.1.4.1.3902.6053.19.1.3.11.1.30728.25
    trapOtherChassisBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 25}

-- 1.3.6.1.4.1.3902.6053.19.1.3.11.1.30728.26
    trapDiskDriveVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 26}

-- 1.3.6.1.4.1.3902.6053.19.1.3.11.1.30728.27
    trapPeripheralBayVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 27}

-- 1.3.6.1.4.1.3902.6053.19.1.3.11.1.30728.28
    trapDeviceBayVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 28}

-- 1.3.6.1.4.1.3902.6053.19.1.3.11.1.30728.29
    trapFanCoolingVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 29}

-- 1.3.6.1.4.1.3902.6053.19.1.3.11.1.30728.30
    trapCoolingUnitVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 30}

-- 1.3.6.1.4.1.3902.6053.19.1.3.11.1.30728.31
    trapCableInterconnectVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 31}

-- 1.3.6.1.4.1.3902.6053.19.1.3.11.1.30728.32
    trapMemoryDeviceVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 32}

-- 1.3.6.1.4.1.3902.6053.19.1.3.11.1.30728.33
    trapSystemManagementSoftwareVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 33}

-- 1.3.6.1.4.1.3902.6053.19.1.3.11.1.30728.34
    trapBiosVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 34}

-- 1.3.6.1.4.1.3902.6053.19.1.3.11.1.30728.35
    trapOperatingSystemVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 35}

-- 1.3.6.1.4.1.3902.6053.19.1.3.11.1.30728.36
    trapSystemBusVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 36}

-- 1.3.6.1.4.1.3902.6053.19.1.3.11.1.30728.37
    trapGroupVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 37}

-- 1.3.6.1.4.1.3902.6053.19.1.3.11.1.30728.38
    trapRemotManagementDeviceVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 38}

-- 1.3.6.1.4.1.3902.6053.19.1.3.11.1.30728.39
    trapExternalEnvironmentVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 39}

-- 1.3.6.1.4.1.3902.6053.19.1.3.11.1.30728.40
    trapBatteryVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 40}

-- 1.3.6.1.4.1.3902.6053.19.1.3.11.1.30728.41
    trapProcessBladeModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 41}

-- 1.3.6.1.4.1.3902.6053.19.1.3.11.1.30728.42
    trapConnectivitySwitchVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 42}

-- 1.3.6.1.4.1.3902.6053.19.1.3.11.1.30728.43
    trapProcessorMemoryModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 43}

-- 1.3.6.1.4.1.3902.6053.19.1.3.11.1.30728.44
    trapIOModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 44}

-- 1.3.6.1.4.1.3902.6053.19.1.3.11.1.30728.45
    trapProcessorIOModuleVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 45}

-- 1.3.6.1.4.1.3902.6053.19.1.3.11.1.30728.46
    trapMGMTControllerFirmwareVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 46}

-- 1.3.6.1.4.1.3902.6053.19.1.3.11.1.30728.47
    trapIPMIChannelVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 47}

-- 1.3.6.1.4.1.3902.6053.19.1.3.11.1.30728.48
    trapPCIBUSVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 48}

-- 1.3.6.1.4.1.3902.6053.19.1.3.11.1.30728.49
    trapPCIExpressBUSVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 49}

-- 1.3.6.1.4.1.3902.6053.19.1.3.11.1.30728.50
    trapSCSIBUSVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 50}

-- 1.3.6.1.4.1.3902.6053.19.1.3.11.1.30728.51
    trapSATASASBUSVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 51}

-- 1.3.6.1.4.1.3902.6053.19.1.3.11.1.30728.52
    trapProcessorFrontSideBUSVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 52}

-- 1.3.6.1.4.1.3902.6053.19.1.3.11.1.30728.53
    trapRealTimeClockVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 53}

-- 1.3.6.1.4.1.3902.6053.19.1.3.11.1.30728.54
    trapSystemFirmwareVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 54}

-- 1.3.6.1.4.1.3902.6053.19.1.3.11.1.30728.160
    trapMainBoardVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 160}

-- 1.3.6.1.4.1.3902.6053.19.1.3.11.1.30728.208
    trapNetPortVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 208}

-- 1.3.6.1.4.1.3902.6053.19.1.3.11.1.30728.209
    trapLogicalDiskVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 209}

-- 1.3.6.1.4.1.3902.6053.19.1.3.11.1.30728.210
    trapStorageCTRLVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 210}

-- 1.3.6.1.4.1.3902.6053.19.1.3.11.1.30728.272
    trapNICSFPVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 272}

-- 1.3.6.1.4.1.3902.6053.19.1.3.11.1.30728.273
    trapOCPSFPVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 273}

-- 1.3.6.1.4.1.3902.6053.19.1.3.11.1.30728.275
    trapSNICSFPVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 28}

-- 1.3.6.1.4.1.3902.6053.19.1.3.11.1.30728.277
    trapDPUT100VoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 277}

-- 1.3.6.1.4.1.3902.6053.19.1.3.11.1.30728.278
    trapDPUT200VoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 278}

-- 1.3.6.1.4.1.3902.6053.19.1.3.11.1.30728.279
    trapBSC25GVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 279}

-- 1.3.6.1.4.1.3902.6053.19.1.3.11.1.30728.281
    trapNEOVoltageIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30728-ucFruId, trap-30728-aucCurrentValue, trap-30728-aucThresholdValue, trap-30728-aucUnitStr, trap-30728-aucSensorName, acTrapTime, acTrapEventSubject, acTrapSeverity, acTrapDescription, acTrapProductSerial, acTrapState, acTrapDeviceSN, acTrapAddInform, dwTrapIndex
		                                        }
		STATUS			current
		DESCRIPTION		"Voltage is lower than lower-critical threshold"
		::=  {  trap-30728-reasoninfo 281}

-- 1.3.6.1.4.1.3902.6053.19.1.3.11.1.30729
    trap-30729-addinfo OBJECT IDENTIFIER ::= {trap-addinfo 30729}

-- 1.3.6.1.4.1.3902.6053.19.1.3.11.2.30729.1
    trap-30729-ucFruId OBJECT-TYPE
        SYNTAX Unsigned32
        ACCESS accessible-for-notify
        STATUS current
        DESCRIPTION 
            "FRU ID"
        ::= {trap-30729-addinfo 1}

-- 1.3.6.1.4.1.3902.6053.19.1.3.11.2.30729.5
    trap-30729-aucCurrentValue OBJECT-TYPE
        SYNTAX DisplayString
        ACCESS accessible-for-notify
        STATUS current
        DESCRIPTION 
            "Current value"
        ::= {trap-30729-addinfo 5}

-- 1.3.6.1.4.1.3902.6053.19.1.3.11.2.30729.6
    trap-30729-aucThresholdValue OBJECT-TYPE
        SYNTAX DisplayString
        ACCESS accessible-for-notify
        STATUS current
        DESCRIPTION 
            "Threshold value"
        ::= {trap-30729-addinfo 6}

-- 1.3.6.1.4.1.3902.6053.19.1.3.11.2.30729.7
    trap-30729-aucUnitStr OBJECT-TYPE
        SYNTAX DisplayString
        ACCESS accessible-for-notify
        STATUS current
        DESCRIPTION 
            "Unit"
        ::= {trap-30729-addinfo 7}

-- 1.3.6.1.4.1.3902.6053.19.1.3.11.2.30729.8
    trap-30729-aucSensorName OBJECT-TYPE
        SYNTAX DisplayString
        ACCESS accessible-for-notify
        STATUS current
        DESCRIPTION 
            "Sensor name"
        ::= {trap-30729-addinfo 8}

-- 1.3.6.1.4.1.3902.6053.19.1.3.11.1.30729
    trapVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-alarm 30729}

-- 1.3.6.1.4.1.3902.6053.19.1.3.11.1.30729
    trap-30729-reasoninfo OBJECT IDENTIFIER ::= {trap-alarm 30729}

-- 1.3.6.1.4.1.3902.6053.19.1.3.11.1.30729.0
    trapUnspecifiedVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 0}

-- 1.3.6.1.4.1.3902.6053.19.1.3.11.1.30729.1
    trapOtherVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 1}

-- 1.3.6.1.4.1.3902.6053.19.1.3.11.1.30729.2
    trapUnkownVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 2}

-- 1.3.6.1.4.1.3902.6053.19.1.3.11.1.30729.3
    trapProcessorVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 3}

-- 1.3.6.1.4.1.3902.6053.19.1.3.11.1.30729.4
    trapDiskVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 4}

-- 1.3.6.1.4.1.3902.6053.19.1.3.11.1.30729.5
    trapPeripheralVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 5}

-- 1.3.6.1.4.1.3902.6053.19.1.3.11.1.30729.6
    trapSystemManagementModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 6}

-- 1.3.6.1.4.1.3902.6053.19.1.3.11.1.30729.7
    trapSystemBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 7}

-- 1.3.6.1.4.1.3902.6053.19.1.3.11.1.30729.8
    trapMemoryVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 8}

-- 1.3.6.1.4.1.3902.6053.19.1.3.11.1.30729.9
    trapProcessorModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 9}

-- 1.3.6.1.4.1.3902.6053.19.1.3.11.1.30729.10
    trapPowerSupplyVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 10}

-- 1.3.6.1.4.1.3902.6053.19.1.3.11.1.30729.11
    trapADDINCardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 11}

-- 1.3.6.1.4.1.3902.6053.19.1.3.11.1.30729.12
    trapFrontPanelBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 12}

-- 1.3.6.1.4.1.3902.6053.19.1.3.11.1.30729.13
    trapBackPanelBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 13}

-- 1.3.6.1.4.1.3902.6053.19.1.3.11.1.30729.14
    trapPowerSystemBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 14}

-- 1.3.6.1.4.1.3902.6053.19.1.3.11.1.30729.15
    trapDriveBackplaneVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 15}

-- 1.3.6.1.4.1.3902.6053.19.1.3.11.1.30729.16
    trapSystemInternalExpansionBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 16}

-- 1.3.6.1.4.1.3902.6053.19.1.3.11.1.30729.17
    trapOtherSystemBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 17}

-- 1.3.6.1.4.1.3902.6053.19.1.3.11.1.30729.18
    trapProcessorBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 18}

-- 1.3.6.1.4.1.3902.6053.19.1.3.11.1.30729.19
    trapPowerUnitVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 19}

-- 1.3.6.1.4.1.3902.6053.19.1.3.11.1.30729.20
    trapPowerModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 20}

-- 1.3.6.1.4.1.3902.6053.19.1.3.11.1.30729.21
    trapPowerManagementBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 21}

-- 1.3.6.1.4.1.3902.6053.19.1.3.11.1.30729.22
    trapChassisBackPanelBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 22}

-- 1.3.6.1.4.1.3902.6053.19.1.3.11.1.30729.23
    trapSystemChassisVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 23}

-- 1.3.6.1.4.1.3902.6053.19.1.3.11.1.30729.24
    trapSUBChassisVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 24}

-- 1.3.6.1.4.1.3902.6053.19.1.3.11.1.30729.25
    trapOtherChassisBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 25}

-- 1.3.6.1.4.1.3902.6053.19.1.3.11.1.30729.26
    trapDiskDriveVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 26}

-- 1.3.6.1.4.1.3902.6053.19.1.3.11.1.30729.27
    trapPeripheralBayVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 27}

-- 1.3.6.1.4.1.3902.6053.19.1.3.11.1.30729.28
    trapDeviceBayVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 28}

-- 1.3.6.1.4.1.3902.6053.19.1.3.11.1.30729.29
    trapFanCoolingVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 29}

-- 1.3.6.1.4.1.3902.6053.19.1.3.11.1.30729.30
    trapCoolingUnitVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 30}

-- 1.3.6.1.4.1.3902.6053.19.1.3.11.1.30729.31
    trapCableInterconnectVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 31}

-- 1.3.6.1.4.1.3902.6053.19.1.3.11.1.30729.32
    trapMemoryDeviceVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 32}

-- 1.3.6.1.4.1.3902.6053.19.1.3.11.1.30729.33
    trapSystemManagementSoftwareVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 33}

-- 1.3.6.1.4.1.3902.6053.19.1.3.11.1.30729.34
    trapBiosVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 34}

-- 1.3.6.1.4.1.3902.6053.19.1.3.11.1.30729.35
    trapOperatingSystemVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 35}

-- 1.3.6.1.4.1.3902.6053.19.1.3.11.1.30729.36
    trapSystemBusVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 36}

-- 1.3.6.1.4.1.3902.6053.19.1.3.11.1.30729.37
    trapGroupVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 37}

-- 1.3.6.1.4.1.3902.6053.19.1.3.11.1.30729.38
    trapRemotManagementDeviceVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 38}

-- 1.3.6.1.4.1.3902.6053.19.1.3.11.1.30729.39
    trapExternalEnvironmentVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 39}

-- 1.3.6.1.4.1.3902.6053.19.1.3.11.1.30729.40
    trapBatteryVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 40}

-- 1.3.6.1.4.1.3902.6053.19.1.3.11.1.30729.41
    trapProcessBladeModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 41}

-- 1.3.6.1.4.1.3902.6053.19.1.3.11.1.30729.42
    trapConnectivitySwitchVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 42}

-- 1.3.6.1.4.1.3902.6053.19.1.3.11.1.30729.43
    trapProcessorMemoryModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 43}

-- 1.3.6.1.4.1.3902.6053.19.1.3.11.1.30729.44
    trapIOModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 44}

-- 1.3.6.1.4.1.3902.6053.19.1.3.11.1.30729.45
    trapProcessorIOModuleVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 45}

-- 1.3.6.1.4.1.3902.6053.19.1.3.11.1.30729.46
    trapMGMTControllerFirmwareVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 46}

-- 1.3.6.1.4.1.3902.6053.19.1.3.11.1.30729.47
    trapIPMIChannelVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 47}

-- 1.3.6.1.4.1.3902.6053.19.1.3.11.1.30729.48
    trapPCIBUSVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 48}

-- 1.3.6.1.4.1.3902.6053.19.1.3.11.1.30729.49
    trapPCIExpressBUSVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 49}

-- 1.3.6.1.4.1.3902.6053.19.1.3.11.1.30729.50
    trapSCSIBUSVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 50}

-- 1.3.6.1.4.1.3902.6053.19.1.3.11.1.30729.51
    trapSATASASBUSVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 51}

-- 1.3.6.1.4.1.3902.6053.19.1.3.11.1.30729.52
    trapProcessorFrontSideBUSVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 52}

-- 1.3.6.1.4.1.3902.6053.19.1.3.11.1.30729.53
    trapRealTimeClockVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 53}

-- 1.3.6.1.4.1.3902.6053.19.1.3.11.1.30729.54
    trapSystemFirmwareVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 54}

-- 1.3.6.1.4.1.3902.6053.19.1.3.11.1.30729.160
    trapMainBoardVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 160}

-- 1.3.6.1.4.1.3902.6053.19.1.3.11.1.30729.208
    trapNetPortVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 208}

-- 1.3.6.1.4.1.3902.6053.19.1.3.11.1.30729.209
    trapLogicalDiskVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 209}

-- 1.3.6.1.4.1.3902.6053.19.1.3.11.1.30729.210
    trapStorageCTRLVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 210}

-- 1.3.6.1.4.1.3902.6053.19.1.3.11.1.30729.272
    trapNICSFPVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 272}

-- 1.3.6.1.4.1.3902.6053.19.1.3.11.1.30729.273
    trapOCPSFPVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 273}

-- 1.3.6.1.4.1.3902.6053.19.1.3.11.1.30729.275
    trapSNICSFPVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 28}

-- 1.3.6.1.4.1.3902.6053.19.1.3.11.1.30729.277
    trapDPUT100VoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 277}

-- 1.3.6.1.4.1.3902.6053.19.1.3.11.1.30729.278
    trapDPUT200VoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 278}

-- 1.3.6.1.4.1.3902.6053.19.1.3.11.1.30729.279
    trapBSC25GVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 279}

-- 1.3.6.1.4.1.3902.6053.19.1.3.11.1.30729.281
    trapNEOVoltageIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30729-ucFruId, trap-30729-aucCurrentValue, trap-30729-aucThresholdValue, trap-30729-aucUnitStr, trap-30729-aucSensorName, acTrapTime, acTrapEventSubject, acTrapSeverity, acTrapDescription, acTrapProductSerial, acTrapState, acTrapDeviceSN, acTrapAddInform, dwTrapIndex
		                                        }
		STATUS			current
		DESCRIPTION		"Voltage is lower than lower-non-recoverable threshold."
		::=  {  trap-30729-reasoninfo 281}

-- 1.3.6.1.4.1.3902.6053.19.1.3.11.1.30730
    trap-30730-addinfo OBJECT IDENTIFIER ::= {trap-addinfo 30730}

-- 1.3.6.1.4.1.3902.6053.19.1.3.11.2.30730.1
    trap-30730-ucFruId OBJECT-TYPE
        SYNTAX Unsigned32
        ACCESS accessible-for-notify
        STATUS current
        DESCRIPTION 
            "FRU ID"
        ::= {trap-30730-addinfo 1}

-- 1.3.6.1.4.1.3902.6053.19.1.3.11.2.30730.5
    trap-30730-aucCurrentValue OBJECT-TYPE
        SYNTAX DisplayString
        ACCESS accessible-for-notify
        STATUS current
        DESCRIPTION 
            "Current value"
        ::= {trap-30730-addinfo 5}

-- 1.3.6.1.4.1.3902.6053.19.1.3.11.2.30730.6
    trap-30730-aucThresholdValue OBJECT-TYPE
        SYNTAX DisplayString
        ACCESS accessible-for-notify
        STATUS current
        DESCRIPTION 
            "Threshold value"
        ::= {trap-30730-addinfo 6}

-- 1.3.6.1.4.1.3902.6053.19.1.3.11.2.30730.7
    trap-30730-aucUnitStr OBJECT-TYPE
        SYNTAX DisplayString
        ACCESS accessible-for-notify
        STATUS current
        DESCRIPTION 
            "Unit"
        ::= {trap-30730-addinfo 7}

-- 1.3.6.1.4.1.3902.6053.19.1.3.11.2.30730.8
    trap-30730-aucSensorName OBJECT-TYPE
        SYNTAX DisplayString
        ACCESS accessible-for-notify
        STATUS current
        DESCRIPTION 
            "Sensor name"
        ::= {trap-30730-addinfo 8}

-- 1.3.6.1.4.1.3902.6053.19.1.3.11.1.30730
    trapVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-alarm 30730}

-- 1.3.6.1.4.1.3902.6053.19.1.3.11.1.30730
    trap-30730-reasoninfo OBJECT IDENTIFIER ::= {trap-alarm 30730}

-- 1.3.6.1.4.1.3902.6053.19.1.3.11.1.30730.0
    trapUnspecifiedVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 0}

-- 1.3.6.1.4.1.3902.6053.19.1.3.11.1.30730.1
    trapOtherVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 1}

-- 1.3.6.1.4.1.3902.6053.19.1.3.11.1.30730.2
    trapUnkownVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 2}

-- 1.3.6.1.4.1.3902.6053.19.1.3.11.1.30730.3
    trapProcessorVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 3}

-- 1.3.6.1.4.1.3902.6053.19.1.3.11.1.30730.4
    trapDiskVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 4}

-- 1.3.6.1.4.1.3902.6053.19.1.3.11.1.30730.5
    trapPeripheralVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 5}

-- 1.3.6.1.4.1.3902.6053.19.1.3.11.1.30730.6
    trapSystemManagementModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 6}

-- 1.3.6.1.4.1.3902.6053.19.1.3.11.1.30730.7
    trapSystemBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 7}

-- 1.3.6.1.4.1.3902.6053.19.1.3.11.1.30730.8
    trapMemoryVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 8}

-- 1.3.6.1.4.1.3902.6053.19.1.3.11.1.30730.9
    trapProcessorModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 9}

-- 1.3.6.1.4.1.3902.6053.19.1.3.11.1.30730.10
    trapPowerSupplyVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 10}

-- 1.3.6.1.4.1.3902.6053.19.1.3.11.1.30730.11
    trapADDINCardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 11}

-- 1.3.6.1.4.1.3902.6053.19.1.3.11.1.30730.12
    trapFrontPanelBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 12}

-- 1.3.6.1.4.1.3902.6053.19.1.3.11.1.30730.13
    trapBackPanelBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 13}

-- 1.3.6.1.4.1.3902.6053.19.1.3.11.1.30730.14
    trapPowerSystemBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 14}

-- 1.3.6.1.4.1.3902.6053.19.1.3.11.1.30730.15
    trapDriveBackplaneVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 15}

-- 1.3.6.1.4.1.3902.6053.19.1.3.11.1.30730.16
    trapSystemInternalExpansionBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 16}

-- 1.3.6.1.4.1.3902.6053.19.1.3.11.1.30730.17
    trapOtherSystemBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 17}

-- 1.3.6.1.4.1.3902.6053.19.1.3.11.1.30730.18
    trapProcessorBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 18}

-- 1.3.6.1.4.1.3902.6053.19.1.3.11.1.30730.19
    trapPowerUnitVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 19}

-- 1.3.6.1.4.1.3902.6053.19.1.3.11.1.30730.20
    trapPowerModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 20}

-- 1.3.6.1.4.1.3902.6053.19.1.3.11.1.30730.21
    trapPowerManagementBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 21}

-- 1.3.6.1.4.1.3902.6053.19.1.3.11.1.30730.22
    trapChassisBackPanelBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 22}

-- 1.3.6.1.4.1.3902.6053.19.1.3.11.1.30730.23
    trapSystemChassisVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 23}

-- 1.3.6.1.4.1.3902.6053.19.1.3.11.1.30730.24
    trapSUBChassisVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 24}

-- 1.3.6.1.4.1.3902.6053.19.1.3.11.1.30730.25
    trapOtherChassisBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 25}

-- 1.3.6.1.4.1.3902.6053.19.1.3.11.1.30730.26
    trapDiskDriveVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 26}

-- 1.3.6.1.4.1.3902.6053.19.1.3.11.1.30730.27
    trapPeripheralBayVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 27}

-- 1.3.6.1.4.1.3902.6053.19.1.3.11.1.30730.28
    trapDeviceBayVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 28}

-- 1.3.6.1.4.1.3902.6053.19.1.3.11.1.30730.29
    trapFanCoolingVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 29}

-- 1.3.6.1.4.1.3902.6053.19.1.3.11.1.30730.30
    trapCoolingUnitVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 30}

-- 1.3.6.1.4.1.3902.6053.19.1.3.11.1.30730.31
    trapCableInterconnectVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 31}

-- 1.3.6.1.4.1.3902.6053.19.1.3.11.1.30730.32
    trapMemoryDeviceVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 32}

-- 1.3.6.1.4.1.3902.6053.19.1.3.11.1.30730.33
    trapSystemManagementSoftwareVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 33}

-- 1.3.6.1.4.1.3902.6053.19.1.3.11.1.30730.34
    trapBiosVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 34}

-- 1.3.6.1.4.1.3902.6053.19.1.3.11.1.30730.35
    trapOperatingSystemVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 35}

-- 1.3.6.1.4.1.3902.6053.19.1.3.11.1.30730.36
    trapSystemBusVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 36}

-- 1.3.6.1.4.1.3902.6053.19.1.3.11.1.30730.37
    trapGroupVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 37}

-- 1.3.6.1.4.1.3902.6053.19.1.3.11.1.30730.38
    trapRemotManagementDeviceVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 38}

-- 1.3.6.1.4.1.3902.6053.19.1.3.11.1.30730.39
    trapExternalEnvironmentVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 39}

-- 1.3.6.1.4.1.3902.6053.19.1.3.11.1.30730.40
    trapBatteryVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 40}

-- 1.3.6.1.4.1.3902.6053.19.1.3.11.1.30730.41
    trapProcessBladeModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 41}

-- 1.3.6.1.4.1.3902.6053.19.1.3.11.1.30730.42
    trapConnectivitySwitchVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 42}

-- 1.3.6.1.4.1.3902.6053.19.1.3.11.1.30730.43
    trapProcessorMemoryModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 43}

-- 1.3.6.1.4.1.3902.6053.19.1.3.11.1.30730.44
    trapIOModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 44}

-- 1.3.6.1.4.1.3902.6053.19.1.3.11.1.30730.45
    trapProcessorIOModuleVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 45}

-- 1.3.6.1.4.1.3902.6053.19.1.3.11.1.30730.46
    trapMGMTControllerFirmwareVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 46}

-- 1.3.6.1.4.1.3902.6053.19.1.3.11.1.30730.47
    trapIPMIChannelVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 47}

-- 1.3.6.1.4.1.3902.6053.19.1.3.11.1.30730.48
    trapPCIBUSVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 48}

-- 1.3.6.1.4.1.3902.6053.19.1.3.11.1.30730.49
    trapPCIExpressBUSVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 49}

-- 1.3.6.1.4.1.3902.6053.19.1.3.11.1.30730.50
    trapSCSIBUSVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 50}

-- 1.3.6.1.4.1.3902.6053.19.1.3.11.1.30730.51
    trapSATASASBUSVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 51}

-- 1.3.6.1.4.1.3902.6053.19.1.3.11.1.30730.52
    trapProcessorFrontSideBUSVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 52}

-- 1.3.6.1.4.1.3902.6053.19.1.3.11.1.30730.53
    trapRealTimeClockVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 53}

-- 1.3.6.1.4.1.3902.6053.19.1.3.11.1.30730.54
    trapSystemFirmwareVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 54}

-- 1.3.6.1.4.1.3902.6053.19.1.3.11.1.30730.160
    trapMainBoardVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 160}

-- 1.3.6.1.4.1.3902.6053.19.1.3.11.1.30730.208
    trapNetPortVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 208}

-- 1.3.6.1.4.1.3902.6053.19.1.3.11.1.30730.209
    trapLogicalDiskVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 209}

-- 1.3.6.1.4.1.3902.6053.19.1.3.11.1.30730.210
    trapStorageCTRLVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 210}

-- 1.3.6.1.4.1.3902.6053.19.1.3.11.1.30730.272
    trapNICSFPVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 272}

-- 1.3.6.1.4.1.3902.6053.19.1.3.11.1.30730.273
    trapOCPSFPVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 273}

-- 1.3.6.1.4.1.3902.6053.19.1.3.11.1.30730.275
    trapSNICSFPVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 28}

-- 1.3.6.1.4.1.3902.6053.19.1.3.11.1.30730.277
    trapDPUT100VoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 277}

-- 1.3.6.1.4.1.3902.6053.19.1.3.11.1.30730.278
    trapDPUT200VoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 278}

-- 1.3.6.1.4.1.3902.6053.19.1.3.11.1.30730.279
    trapBSC25GVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 279}

-- 1.3.6.1.4.1.3902.6053.19.1.3.11.1.30730.281
    trapNEOVoltageIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30730-ucFruId, trap-30730-aucCurrentValue, trap-30730-aucThresholdValue, trap-30730-aucUnitStr, trap-30730-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-critical threshold."
		::=  {  trap-30730-reasoninfo 281}

-- 1.3.6.1.4.1.3902.6053.19.1.3.11.1.30731
    trap-30731-addinfo OBJECT IDENTIFIER ::= {trap-addinfo 30731}

-- 1.3.6.1.4.1.3902.6053.19.1.3.11.2.30731.1
    trap-30731-ucFruId OBJECT-TYPE
        SYNTAX Unsigned32
        ACCESS accessible-for-notify
        STATUS current
        DESCRIPTION 
            "FRU ID"
        ::= {trap-30731-addinfo 1}

-- 1.3.6.1.4.1.3902.6053.19.1.3.11.2.30731.5
    trap-30731-aucCurrentValue OBJECT-TYPE
        SYNTAX DisplayString
        ACCESS accessible-for-notify
        STATUS current
        DESCRIPTION 
            "Current value"
        ::= {trap-30731-addinfo 5}

-- 1.3.6.1.4.1.3902.6053.19.1.3.11.2.30731.6
    trap-30731-aucThresholdValue OBJECT-TYPE
        SYNTAX DisplayString
        ACCESS accessible-for-notify
        STATUS current
        DESCRIPTION 
            "Threshold value"
        ::= {trap-30731-addinfo 6}

-- 1.3.6.1.4.1.3902.6053.19.1.3.11.2.30731.7
    trap-30731-aucUnitStr OBJECT-TYPE
        SYNTAX DisplayString
        ACCESS accessible-for-notify
        STATUS current
        DESCRIPTION 
            "Unit"
        ::= {trap-30731-addinfo 7}

-- 1.3.6.1.4.1.3902.6053.19.1.3.11.2.30731.8
    trap-30731-aucSensorName OBJECT-TYPE
        SYNTAX DisplayString
        ACCESS accessible-for-notify
        STATUS current
        DESCRIPTION 
            "Sensor name"
        ::= {trap-30731-addinfo 8}

-- 1.3.6.1.4.1.3902.6053.19.1.3.11.1.30731
    trapVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-alarm 30731}

-- 1.3.6.1.4.1.3902.6053.19.1.3.11.1.30731
    trap-30731-reasoninfo OBJECT IDENTIFIER ::= {trap-alarm 30731}

-- 1.3.6.1.4.1.3902.6053.19.1.3.11.1.30731.0
    trapUnspecifiedVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 0}

-- 1.3.6.1.4.1.3902.6053.19.1.3.11.1.30731.1
    trapOtherVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 1}

-- 1.3.6.1.4.1.3902.6053.19.1.3.11.1.30731.2
    trapUnkownVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 2}

-- 1.3.6.1.4.1.3902.6053.19.1.3.11.1.30731.3
    trapProcessorVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 3}

-- 1.3.6.1.4.1.3902.6053.19.1.3.11.1.30731.4
    trapDiskVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 4}

-- 1.3.6.1.4.1.3902.6053.19.1.3.11.1.30731.5
    trapPeripheralVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 5}

-- 1.3.6.1.4.1.3902.6053.19.1.3.11.1.30731.6
    trapSystemManagementModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 6}

-- 1.3.6.1.4.1.3902.6053.19.1.3.11.1.30731.7
    trapSystemBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 7}

-- 1.3.6.1.4.1.3902.6053.19.1.3.11.1.30731.8
    trapMemoryVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 8}

-- 1.3.6.1.4.1.3902.6053.19.1.3.11.1.30731.9
    trapProcessorModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 9}

-- 1.3.6.1.4.1.3902.6053.19.1.3.11.1.30731.10
    trapPowerSupplyVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 10}

-- 1.3.6.1.4.1.3902.6053.19.1.3.11.1.30731.11
    trapADDINCardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 11}

-- 1.3.6.1.4.1.3902.6053.19.1.3.11.1.30731.12
    trapFrontPanelBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 12}

-- 1.3.6.1.4.1.3902.6053.19.1.3.11.1.30731.13
    trapBackPanelBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 13}

-- 1.3.6.1.4.1.3902.6053.19.1.3.11.1.30731.14
    trapPowerSystemBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 14}

-- 1.3.6.1.4.1.3902.6053.19.1.3.11.1.30731.15
    trapDriveBackplaneVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 15}

-- 1.3.6.1.4.1.3902.6053.19.1.3.11.1.30731.16
    trapSystemInternalExpansionBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 16}

-- 1.3.6.1.4.1.3902.6053.19.1.3.11.1.30731.17
    trapOtherSystemBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 17}

-- 1.3.6.1.4.1.3902.6053.19.1.3.11.1.30731.18
    trapProcessorBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 18}

-- 1.3.6.1.4.1.3902.6053.19.1.3.11.1.30731.19
    trapPowerUnitVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 19}

-- 1.3.6.1.4.1.3902.6053.19.1.3.11.1.30731.20
    trapPowerModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 20}

-- 1.3.6.1.4.1.3902.6053.19.1.3.11.1.30731.21
    trapPowerManagementBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 21}

-- 1.3.6.1.4.1.3902.6053.19.1.3.11.1.30731.22
    trapChassisBackPanelBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 22}

-- 1.3.6.1.4.1.3902.6053.19.1.3.11.1.30731.23
    trapSystemChassisVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 23}

-- 1.3.6.1.4.1.3902.6053.19.1.3.11.1.30731.24
    trapSUBChassisVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 24}

-- 1.3.6.1.4.1.3902.6053.19.1.3.11.1.30731.25
    trapOtherChassisBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 25}

-- 1.3.6.1.4.1.3902.6053.19.1.3.11.1.30731.26
    trapDiskDriveVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 26}

-- 1.3.6.1.4.1.3902.6053.19.1.3.11.1.30731.27
    trapPeripheralBayVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 27}

-- 1.3.6.1.4.1.3902.6053.19.1.3.11.1.30731.28
    trapDeviceBayVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 28}

-- 1.3.6.1.4.1.3902.6053.19.1.3.11.1.30731.29
    trapFanCoolingVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 29}

-- 1.3.6.1.4.1.3902.6053.19.1.3.11.1.30731.30
    trapCoolingUnitVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 30}

-- 1.3.6.1.4.1.3902.6053.19.1.3.11.1.30731.31
    trapCableInterconnectVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 31}

-- 1.3.6.1.4.1.3902.6053.19.1.3.11.1.30731.32
    trapMemoryDeviceVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 32}

-- 1.3.6.1.4.1.3902.6053.19.1.3.11.1.30731.33
    trapSystemManagementSoftwareVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 33}

-- 1.3.6.1.4.1.3902.6053.19.1.3.11.1.30731.34
    trapBiosVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 34}

-- 1.3.6.1.4.1.3902.6053.19.1.3.11.1.30731.35
    trapOperatingSystemVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 35}

-- 1.3.6.1.4.1.3902.6053.19.1.3.11.1.30731.36
    trapSystemBusVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 36}

-- 1.3.6.1.4.1.3902.6053.19.1.3.11.1.30731.37
    trapGroupVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 37}

-- 1.3.6.1.4.1.3902.6053.19.1.3.11.1.30731.38
    trapRemotManagementDeviceVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 38}

-- 1.3.6.1.4.1.3902.6053.19.1.3.11.1.30731.39
    trapExternalEnvironmentVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 39}

-- 1.3.6.1.4.1.3902.6053.19.1.3.11.1.30731.40
    trapBatteryVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 40}

-- 1.3.6.1.4.1.3902.6053.19.1.3.11.1.30731.41
    trapProcessBladeModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 41}

-- 1.3.6.1.4.1.3902.6053.19.1.3.11.1.30731.42
    trapConnectivitySwitchVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 42}

-- 1.3.6.1.4.1.3902.6053.19.1.3.11.1.30731.43
    trapProcessorMemoryModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 43}

-- 1.3.6.1.4.1.3902.6053.19.1.3.11.1.30731.44
    trapIOModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 44}

-- 1.3.6.1.4.1.3902.6053.19.1.3.11.1.30731.45
    trapProcessorIOModuleVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 45}

-- 1.3.6.1.4.1.3902.6053.19.1.3.11.1.30731.46
    trapMGMTControllerFirmwareVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 46}

-- 1.3.6.1.4.1.3902.6053.19.1.3.11.1.30731.47
    trapIPMIChannelVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 47}

-- 1.3.6.1.4.1.3902.6053.19.1.3.11.1.30731.48
    trapPCIBUSVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 48}

-- 1.3.6.1.4.1.3902.6053.19.1.3.11.1.30731.49
    trapPCIExpressBUSVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 49}

-- 1.3.6.1.4.1.3902.6053.19.1.3.11.1.30731.50
    trapSCSIBUSVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 50}

-- 1.3.6.1.4.1.3902.6053.19.1.3.11.1.30731.51
    trapSATASASBUSVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 51}

-- 1.3.6.1.4.1.3902.6053.19.1.3.11.1.30731.52
    trapProcessorFrontSideBUSVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 52}

-- 1.3.6.1.4.1.3902.6053.19.1.3.11.1.30731.53
    trapRealTimeClockVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 53}

-- 1.3.6.1.4.1.3902.6053.19.1.3.11.1.30731.54
    trapSystemFirmwareVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 54}

-- 1.3.6.1.4.1.3902.6053.19.1.3.11.1.30731.160
    trapMainBoardVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 160}

-- 1.3.6.1.4.1.3902.6053.19.1.3.11.1.30731.208
    trapNetPortVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 208}

-- 1.3.6.1.4.1.3902.6053.19.1.3.11.1.30731.209
    trapLogicalDiskVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 209}

-- 1.3.6.1.4.1.3902.6053.19.1.3.11.1.30731.210
    trapStorageCTRLVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 210}

-- 1.3.6.1.4.1.3902.6053.19.1.3.11.1.30731.272
    trapNICSFPVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 272}

-- 1.3.6.1.4.1.3902.6053.19.1.3.11.1.30731.273
    trapOCPSFPVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 273}

-- 1.3.6.1.4.1.3902.6053.19.1.3.11.1.30731.275
    trapSNICSFPVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 28}

-- 1.3.6.1.4.1.3902.6053.19.1.3.11.1.30731.277
    trapDPUT100VoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 277}

-- 1.3.6.1.4.1.3902.6053.19.1.3.11.1.30731.278
    trapDPUT200VoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 278}

-- 1.3.6.1.4.1.3902.6053.19.1.3.11.1.30731.279
    trapBSC25GVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 279}

-- 1.3.6.1.4.1.3902.6053.19.1.3.11.1.30731.281
    trapNEOVoltageIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30731-ucFruId, trap-30731-aucCurrentValue, trap-30731-aucThresholdValue, trap-30731-aucUnitStr, trap-30731-aucSensorName, acTrapTime, acTrapEventSubject, acTrapSeverity, acTrapDescription, acTrapProductSerial, acTrapState, acTrapDeviceSN, acTrapAddInform, dwTrapIndex
		                                        }
		STATUS			current
		DESCRIPTION		"Voltage is higher than upper-critical threshold."
		::=  {  trap-30731-reasoninfo 281}

-- 1.3.6.1.4.1.3902.6053.19.1.3.11.1.30732
    trap-30732-addinfo OBJECT IDENTIFIER ::= {trap-addinfo 30732}

-- 1.3.6.1.4.1.3902.6053.19.1.3.11.2.30732.1
    trap-30732-ucFruId OBJECT-TYPE
        SYNTAX Unsigned32
        ACCESS accessible-for-notify
        STATUS current
        DESCRIPTION 
            "FRU ID"
        ::= {trap-30732-addinfo 1}

-- 1.3.6.1.4.1.3902.6053.19.1.3.11.2.30732.5
    trap-30732-aucCurrentValue OBJECT-TYPE
        SYNTAX DisplayString
        ACCESS accessible-for-notify
        STATUS current
        DESCRIPTION 
            "Current value"
        ::= {trap-30732-addinfo 5}

-- 1.3.6.1.4.1.3902.6053.19.1.3.11.2.30732.6
    trap-30732-aucThresholdValue OBJECT-TYPE
        SYNTAX DisplayString
        ACCESS accessible-for-notify
        STATUS current
        DESCRIPTION 
            "Threshold value"
        ::= {trap-30732-addinfo 6}

-- 1.3.6.1.4.1.3902.6053.19.1.3.11.2.30732.7
    trap-30732-aucUnitStr OBJECT-TYPE
        SYNTAX DisplayString
        ACCESS accessible-for-notify
        STATUS current
        DESCRIPTION 
            "Unit"
        ::= {trap-30732-addinfo 7}

-- 1.3.6.1.4.1.3902.6053.19.1.3.11.2.30732.8
    trap-30732-aucSensorName OBJECT-TYPE
        SYNTAX DisplayString
        ACCESS accessible-for-notify
        STATUS current
        DESCRIPTION 
            "Sensor name"
        ::= {trap-30732-addinfo 8}

-- 1.3.6.1.4.1.3902.6053.19.1.3.11.1.30732
    trapVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-alarm 30732}

-- 1.3.6.1.4.1.3902.6053.19.1.3.11.1.30732
    trap-30732-reasoninfo OBJECT IDENTIFIER ::= {trap-alarm 30732}

-- 1.3.6.1.4.1.3902.6053.19.1.3.11.1.30732.0
    trapUnspecifiedVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 0}

-- 1.3.6.1.4.1.3902.6053.19.1.3.11.1.30732.1
    trapOtherVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 1}

-- 1.3.6.1.4.1.3902.6053.19.1.3.11.1.30732.2
    trapUnkownVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 2}

-- 1.3.6.1.4.1.3902.6053.19.1.3.11.1.30732.3
    trapProcessorVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 3}

-- 1.3.6.1.4.1.3902.6053.19.1.3.11.1.30732.4
    trapDiskVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 4}

-- 1.3.6.1.4.1.3902.6053.19.1.3.11.1.30732.5
    trapPeripheralVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 5}

-- 1.3.6.1.4.1.3902.6053.19.1.3.11.1.30732.6
    trapSystemManagementModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 6}

-- 1.3.6.1.4.1.3902.6053.19.1.3.11.1.30732.7
    trapSystemBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 7}

-- 1.3.6.1.4.1.3902.6053.19.1.3.11.1.30732.8
    trapMemoryVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 8}

-- 1.3.6.1.4.1.3902.6053.19.1.3.11.1.30732.9
    trapProcessorModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 9}

-- 1.3.6.1.4.1.3902.6053.19.1.3.11.1.30732.10
    trapPowerSupplyVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 10}

-- 1.3.6.1.4.1.3902.6053.19.1.3.11.1.30732.11
    trapADDINCardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 11}

-- 1.3.6.1.4.1.3902.6053.19.1.3.11.1.30732.12
    trapFrontPanelBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 12}

-- 1.3.6.1.4.1.3902.6053.19.1.3.11.1.30732.13
    trapBackPanelBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 13}

-- 1.3.6.1.4.1.3902.6053.19.1.3.11.1.30732.14
    trapPowerSystemBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 14}

-- 1.3.6.1.4.1.3902.6053.19.1.3.11.1.30732.15
    trapDriveBackplaneVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 15}

-- 1.3.6.1.4.1.3902.6053.19.1.3.11.1.30732.16
    trapSystemInternalExpansionBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 16}

-- 1.3.6.1.4.1.3902.6053.19.1.3.11.1.30732.17
    trapOtherSystemBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 17}

-- 1.3.6.1.4.1.3902.6053.19.1.3.11.1.30732.18
    trapProcessorBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 18}

-- 1.3.6.1.4.1.3902.6053.19.1.3.11.1.30732.19
    trapPowerUnitVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 19}

-- 1.3.6.1.4.1.3902.6053.19.1.3.11.1.30732.20
    trapPowerModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 20}

-- 1.3.6.1.4.1.3902.6053.19.1.3.11.1.30732.21
    trapPowerManagementBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 21}

-- 1.3.6.1.4.1.3902.6053.19.1.3.11.1.30732.22
    trapChassisBackPanelBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 22}

-- 1.3.6.1.4.1.3902.6053.19.1.3.11.1.30732.23
    trapSystemChassisVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 23}

-- 1.3.6.1.4.1.3902.6053.19.1.3.11.1.30732.24
    trapSUBChassisVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 24}

-- 1.3.6.1.4.1.3902.6053.19.1.3.11.1.30732.25
    trapOtherChassisBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 25}

-- 1.3.6.1.4.1.3902.6053.19.1.3.11.1.30732.26
    trapDiskDriveVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 26}

-- 1.3.6.1.4.1.3902.6053.19.1.3.11.1.30732.27
    trapPeripheralBayVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 27}

-- 1.3.6.1.4.1.3902.6053.19.1.3.11.1.30732.28
    trapDeviceBayVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 28}

-- 1.3.6.1.4.1.3902.6053.19.1.3.11.1.30732.29
    trapFanCoolingVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 29}

-- 1.3.6.1.4.1.3902.6053.19.1.3.11.1.30732.30
    trapCoolingUnitVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 30}

-- 1.3.6.1.4.1.3902.6053.19.1.3.11.1.30732.31
    trapCableInterconnectVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 31}

-- 1.3.6.1.4.1.3902.6053.19.1.3.11.1.30732.32
    trapMemoryDeviceVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 32}

-- 1.3.6.1.4.1.3902.6053.19.1.3.11.1.30732.33
    trapSystemManagementSoftwareVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 33}

-- 1.3.6.1.4.1.3902.6053.19.1.3.11.1.30732.34
    trapBiosVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 34}

-- 1.3.6.1.4.1.3902.6053.19.1.3.11.1.30732.35
    trapOperatingSystemVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 35}

-- 1.3.6.1.4.1.3902.6053.19.1.3.11.1.30732.36
    trapSystemBusVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 36}

-- 1.3.6.1.4.1.3902.6053.19.1.3.11.1.30732.37
    trapGroupVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 37}

-- 1.3.6.1.4.1.3902.6053.19.1.3.11.1.30732.38
    trapRemotManagementDeviceVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 38}

-- 1.3.6.1.4.1.3902.6053.19.1.3.11.1.30732.39
    trapExternalEnvironmentVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 39}

-- 1.3.6.1.4.1.3902.6053.19.1.3.11.1.30732.40
    trapBatteryVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 40}

-- 1.3.6.1.4.1.3902.6053.19.1.3.11.1.30732.41
    trapProcessBladeModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 41}

-- 1.3.6.1.4.1.3902.6053.19.1.3.11.1.30732.42
    trapConnectivitySwitchVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 42}

-- 1.3.6.1.4.1.3902.6053.19.1.3.11.1.30732.43
    trapProcessorMemoryModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 43}

-- 1.3.6.1.4.1.3902.6053.19.1.3.11.1.30732.44
    trapIOModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 44}

-- 1.3.6.1.4.1.3902.6053.19.1.3.11.1.30732.45
    trapProcessorIOModuleVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 45}

-- 1.3.6.1.4.1.3902.6053.19.1.3.11.1.30732.46
    trapMGMTControllerFirmwareVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 46}

-- 1.3.6.1.4.1.3902.6053.19.1.3.11.1.30732.47
    trapIPMIChannelVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 47}

-- 1.3.6.1.4.1.3902.6053.19.1.3.11.1.30732.48
    trapPCIBUSVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 48}

-- 1.3.6.1.4.1.3902.6053.19.1.3.11.1.30732.49
    trapPCIExpressBUSVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 49}

-- 1.3.6.1.4.1.3902.6053.19.1.3.11.1.30732.50
    trapSCSIBUSVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 50}

-- 1.3.6.1.4.1.3902.6053.19.1.3.11.1.30732.51
    trapSATASASBUSVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 51}

-- 1.3.6.1.4.1.3902.6053.19.1.3.11.1.30732.52
    trapProcessorFrontSideBUSVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 52}

-- 1.3.6.1.4.1.3902.6053.19.1.3.11.1.30732.53
    trapRealTimeClockVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 53}

-- 1.3.6.1.4.1.3902.6053.19.1.3.11.1.30732.54
    trapSystemFirmwareVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 54}

-- 1.3.6.1.4.1.3902.6053.19.1.3.11.1.30732.160
    trapMainBoardVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 160}

-- 1.3.6.1.4.1.3902.6053.19.1.3.11.1.30732.208
    trapNetPortVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 208}

-- 1.3.6.1.4.1.3902.6053.19.1.3.11.1.30732.209
    trapLogicalDiskVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 209}

-- 1.3.6.1.4.1.3902.6053.19.1.3.11.1.30732.210
    trapStorageCTRLVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 210}

-- 1.3.6.1.4.1.3902.6053.19.1.3.11.1.30732.272
    trapNICSFPVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 272}

-- 1.3.6.1.4.1.3902.6053.19.1.3.11.1.30732.273
    trapOCPSFPVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 273}

-- 1.3.6.1.4.1.3902.6053.19.1.3.11.1.30732.275
    trapSNICSFPVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 28}

-- 1.3.6.1.4.1.3902.6053.19.1.3.11.1.30732.277
    trapDPUT100VoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 277}

-- 1.3.6.1.4.1.3902.6053.19.1.3.11.1.30732.278
    trapDPUT200VoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 278}

-- 1.3.6.1.4.1.3902.6053.19.1.3.11.1.30732.279
    trapBSC25GVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 279}

-- 1.3.6.1.4.1.3902.6053.19.1.3.11.1.30732.281
    trapNEOVoltageIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30732-ucFruId, trap-30732-aucCurrentValue, trap-30732-aucThresholdValue, trap-30732-aucUnitStr, trap-30732-aucSensorName, acTrapTime, acTrapEventSubject, acTrapSeverity, acTrapDescription, acTrapProductSerial, acTrapState, acTrapDeviceSN, acTrapAddInform, dwTrapIndex
		                                        }
		STATUS			current
		DESCRIPTION		"Voltage is higher than upper-non-recoverable threshold."
		::=  {  trap-30732-reasoninfo 281}

-- 1.3.6.1.4.1.3902.6053.19.1.3.11.1.30734
    trap-30734-addinfo OBJECT IDENTIFIER ::= {trap-addinfo 30734}

-- 1.3.6.1.4.1.3902.6053.19.1.3.11.2.30734.1
    trap-30734-ucFruId OBJECT-TYPE
        SYNTAX Unsigned32
        ACCESS accessible-for-notify
        STATUS current
        DESCRIPTION 
            "FRU ID"
        ::= {trap-30734-addinfo 1}

-- 1.3.6.1.4.1.3902.6053.19.1.3.11.2.30734.5
    trap-30734-aucCurrentValue OBJECT-TYPE
        SYNTAX DisplayString
        ACCESS accessible-for-notify
        STATUS current
        DESCRIPTION 
            "Current value"
        ::= {trap-30734-addinfo 5}

-- 1.3.6.1.4.1.3902.6053.19.1.3.11.2.30734.6
    trap-30734-aucThresholdValue OBJECT-TYPE
        SYNTAX DisplayString
        ACCESS accessible-for-notify
        STATUS current
        DESCRIPTION 
            "Threshold value"
        ::= {trap-30734-addinfo 6}

-- 1.3.6.1.4.1.3902.6053.19.1.3.11.2.30734.7
    trap-30734-aucUnitStr OBJECT-TYPE
        SYNTAX DisplayString
        ACCESS accessible-for-notify
        STATUS current
        DESCRIPTION 
            "Unit"
        ::= {trap-30734-addinfo 7}

-- 1.3.6.1.4.1.3902.6053.19.1.3.11.2.30734.8
    trap-30734-aucSensorName OBJECT-TYPE
        SYNTAX DisplayString
        ACCESS accessible-for-notify
        STATUS current
        DESCRIPTION 
            "Sensor name"
        ::= {trap-30734-addinfo 8}

-- 1.3.6.1.4.1.3902.6053.19.1.3.11.1.30734
    trapVelocityOfFanIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30734-ucFruId, trap-30734-aucCurrentValue, trap-30734-aucThresholdValue, trap-30734-aucUnitStr, trap-30734-aucSensorName, acTrapTime, acTrapEventSubject, acTrapSeverity, acTrapDescription, acTrapProductSerial, acTrapState, acTrapDeviceSN, acTrapAddInform, dwTrapIndex
		                                        }
		STATUS			current
		DESCRIPTION		"Velocity of fan is lower than lower-critical threshold."
		::=  {  trap-alarm 30734}

-- 1.3.6.1.4.1.3902.6053.19.1.3.11.1.30734
    trap-30734-reasoninfo OBJECT IDENTIFIER ::= {trap-alarm 30734}

-- 1.3.6.1.4.1.3902.6053.19.1.3.11.1.30734.1
    trapSpeedOfFanIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30734-ucFruId, trap-30734-aucCurrentValue, trap-30734-aucThresholdValue, trap-30734-aucUnitStr, trap-30734-aucSensorName, acTrapTime, acTrapEventSubject, acTrapSeverity, acTrapDescription, acTrapProductSerial, acTrapState, acTrapDeviceSN, acTrapAddInform, dwTrapIndex
		                                        }
		STATUS			current
		DESCRIPTION		"Velocity of fan is lower than lower-critical threshold."
		::=  {  trap-30734-reasoninfo 1}

-- 1.3.6.1.4.1.3902.6053.19.1.3.11.1.30736
    trap-30736-addinfo OBJECT IDENTIFIER ::= {trap-addinfo 30736}

-- 1.3.6.1.4.1.3902.6053.19.1.3.11.2.30736.1
    trap-30736-ucAlarmLevel OBJECT-TYPE
        SYNTAX Unsigned32
        ACCESS accessible-for-notify
        STATUS current
        DESCRIPTION 
            "Alarm level"
        ::= {trap-30736-addinfo 1}

-- 1.3.6.1.4.1.3902.6053.19.1.3.11.2.30736.2
    trap-30736-ucUtilization OBJECT-TYPE
        SYNTAX Unsigned32
        ACCESS accessible-for-notify
        STATUS current
        DESCRIPTION 
            "CPU Utilization"
        ::= {trap-30736-addinfo 2}

-- 1.3.6.1.4.1.3902.6053.19.1.3.11.2.30736.3
    trap-30736-auThreshold1 OBJECT-TYPE
        SYNTAX Unsigned32
        ACCESS accessible-for-notify
        STATUS current
        DESCRIPTION 
            "Utilization threshold 1"
        ::= {trap-30736-addinfo 3}

-- 1.3.6.1.4.1.3902.6053.19.1.3.11.2.30736.4
    trap-30736-auThreshold2 OBJECT-TYPE
        SYNTAX Unsigned32
        ACCESS accessible-for-notify
        STATUS current
        DESCRIPTION 
            "Utilization threshold 2"
        ::= {trap-30736-addinfo 4}

-- 1.3.6.1.4.1.3902.6053.19.1.3.11.2.30736.5
    trap-30736-auThreshold3 OBJECT-TYPE
        SYNTAX Unsigned32
        ACCESS accessible-for-notify
        STATUS current
        DESCRIPTION 
            "Utilization threshold 3"
        ::= {trap-30736-addinfo 5}

-- 1.3.6.1.4.1.3902.6053.19.1.3.11.1.30736
    trapCpuUtilizationExceedsAlarmLimit  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-alarm 30736}

-- 1.3.6.1.4.1.3902.6053.19.1.3.11.1.30736
    trap-30736-reasoninfo OBJECT IDENTIFIER ::= {trap-alarm 30736}

-- 1.3.6.1.4.1.3902.6053.19.1.3.11.1.30736.1
    trapCpuUtilizationIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-30736-reasoninfo 1}

-- 1.3.6.1.4.1.3902.6053.19.1.3.11.1.30736.2
    trapCpuUtilizationIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-30736-reasoninfo 2}

-- 1.3.6.1.4.1.3902.6053.19.1.3.11.1.30736.3
    trapCpuUtilizationIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-30736-reasoninfo 3}

-- 1.3.6.1.4.1.3902.6053.19.1.3.11.1.30736.4
    trapCpuUtilizationIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-30736-reasoninfo 4}

-- 1.3.6.1.4.1.3902.6053.19.1.3.11.1.30736.5
    trapCpuUtilizationIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-30736-reasoninfo 5}

-- 1.3.6.1.4.1.3902.6053.19.1.3.11.1.30736.6
    trapCpuUtilizationIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30736-ucAlarmLevel, trap-30736-ucUtilization, trap-30736-auThreshold1, trap-30736-auThreshold2, trap-30736-auThreshold3, acTrapTime, acTrapEventSubject, acTrapSeverity, acTrapDescription, acTrapProductSerial, acTrapState, acTrapDeviceSN, acTrapAddInform, dwTrapIndex
		                                        }
		STATUS			current
		DESCRIPTION		"CPU utilization exceeds alarm limit."
		::=  {  trap-30736-reasoninfo 6}

-- 1.3.6.1.4.1.3902.6053.19.1.3.11.1.30737
    trap-30737-addinfo OBJECT IDENTIFIER ::= {trap-addinfo 30737}

-- 1.3.6.1.4.1.3902.6053.19.1.3.11.2.30737.1
    trap-30737-ucAlarmLevel OBJECT-TYPE
        SYNTAX Unsigned32
        ACCESS accessible-for-notify
        STATUS current
        DESCRIPTION 
            "Alarm level"
        ::= {trap-30737-addinfo 1}

-- 1.3.6.1.4.1.3902.6053.19.1.3.11.2.30737.2
    trap-30737-ucUtilization OBJECT-TYPE
        SYNTAX Unsigned32
        ACCESS accessible-for-notify
        STATUS current
        DESCRIPTION 
            "Memory Utilization"
        ::= {trap-30737-addinfo 2}

-- 1.3.6.1.4.1.3902.6053.19.1.3.11.2.30737.3
    trap-30737-auThreshold1 OBJECT-TYPE
        SYNTAX Unsigned32
        ACCESS accessible-for-notify
        STATUS current
        DESCRIPTION 
            "Utilization threshold 1"
        ::= {trap-30737-addinfo 3}

-- 1.3.6.1.4.1.3902.6053.19.1.3.11.2.30737.4
    trap-30737-auThreshold2 OBJECT-TYPE
        SYNTAX Unsigned32
        ACCESS accessible-for-notify
        STATUS current
        DESCRIPTION 
            "Utilization threshold 2"
        ::= {trap-30737-addinfo 4}

-- 1.3.6.1.4.1.3902.6053.19.1.3.11.2.30737.5
    trap-30737-auThreshold3 OBJECT-TYPE
        SYNTAX Unsigned32
        ACCESS accessible-for-notify
        STATUS current
        DESCRIPTION 
            "Utilization threshold 3"
        ::= {trap-30737-addinfo 5}

-- 1.3.6.1.4.1.3902.6053.19.1.3.11.1.30737
    trapMemoryUtilizationExceedsAlarmLimit  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-alarm 30737}

-- 1.3.6.1.4.1.3902.6053.19.1.3.11.1.30737
    trap-30737-reasoninfo OBJECT IDENTIFIER ::= {trap-alarm 30737}

-- 1.3.6.1.4.1.3902.6053.19.1.3.11.1.30737.1
    trapMemoryUtilizationIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-30737-reasoninfo 1}

-- 1.3.6.1.4.1.3902.6053.19.1.3.11.1.30737.2
    trapMemoryUtilizationIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-30737-reasoninfo 2}

-- 1.3.6.1.4.1.3902.6053.19.1.3.11.1.30737.3
    trapMemoryUtilizationIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-30737-reasoninfo 3}

-- 1.3.6.1.4.1.3902.6053.19.1.3.11.1.30737.4
    trapMemoryUtilizationIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-30737-reasoninfo 4}

-- 1.3.6.1.4.1.3902.6053.19.1.3.11.1.30737.5
    trapMemoryUtilizationIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-30737-reasoninfo 5}

-- 1.3.6.1.4.1.3902.6053.19.1.3.11.1.30737.6
    trapMemoryUtilizationIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30737-ucAlarmLevel, trap-30737-ucUtilization, trap-30737-auThreshold1, trap-30737-auThreshold2, trap-30737-auThreshold3, acTrapTime, acTrapEventSubject, acTrapSeverity, acTrapDescription, acTrapProductSerial, acTrapState, acTrapDeviceSN, acTrapAddInform, dwTrapIndex
		                                        }
		STATUS			current
		DESCRIPTION		"Memory utilization exceeds alarm limit."
		::=  {  trap-30737-reasoninfo 6}

-- 1.3.6.1.4.1.3902.6053.19.1.3.11.1.30739
    trap-30739-addinfo OBJECT IDENTIFIER ::= {trap-addinfo 30739}

-- 1.3.6.1.4.1.3902.6053.19.1.3.11.2.30739.1
    trap-30739-ucFruId OBJECT-TYPE
        SYNTAX Unsigned32
        ACCESS accessible-for-notify
        STATUS current
        DESCRIPTION 
            "FRU ID"
        ::= {trap-30739-addinfo 1}

-- 1.3.6.1.4.1.3902.6053.19.1.3.11.2.30739.5
    trap-30739-aucCurrentValue OBJECT-TYPE
        SYNTAX DisplayString
        ACCESS accessible-for-notify
        STATUS current
        DESCRIPTION 
            "Current value"
        ::= {trap-30739-addinfo 5}

-- 1.3.6.1.4.1.3902.6053.19.1.3.11.2.30739.6
    trap-30739-aucThresholdValue OBJECT-TYPE
        SYNTAX DisplayString
        ACCESS accessible-for-notify
        STATUS current
        DESCRIPTION 
            "Threshold value"
        ::= {trap-30739-addinfo 6}

-- 1.3.6.1.4.1.3902.6053.19.1.3.11.2.30739.7
    trap-30739-aucUnitStr OBJECT-TYPE
        SYNTAX DisplayString
        ACCESS accessible-for-notify
        STATUS current
        DESCRIPTION 
            "Unit"
        ::= {trap-30739-addinfo 7}

-- 1.3.6.1.4.1.3902.6053.19.1.3.11.2.30739.8
    trap-30739-aucSensorName OBJECT-TYPE
        SYNTAX DisplayString
        ACCESS accessible-for-notify
        STATUS current
        DESCRIPTION 
            "Sensor name"
        ::= {trap-30739-addinfo 8}

-- 1.3.6.1.4.1.3902.6053.19.1.3.11.1.30739
    trapCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-alarm 30739}

-- 1.3.6.1.4.1.3902.6053.19.1.3.11.1.30739
    trap-30739-reasoninfo OBJECT IDENTIFIER ::= {trap-alarm 30739}

-- 1.3.6.1.4.1.3902.6053.19.1.3.11.1.30739.0
    trapUnspecifiedCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 0}

-- 1.3.6.1.4.1.3902.6053.19.1.3.11.1.30739.1
    trapOtherCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 1}

-- 1.3.6.1.4.1.3902.6053.19.1.3.11.1.30739.2
    trapUnkownCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 2}

-- 1.3.6.1.4.1.3902.6053.19.1.3.11.1.30739.3
    trapProcessorCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 3}

-- 1.3.6.1.4.1.3902.6053.19.1.3.11.1.30739.4
    trapDiskCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 4}

-- 1.3.6.1.4.1.3902.6053.19.1.3.11.1.30739.5
    trapPeripheralCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 5}

-- 1.3.6.1.4.1.3902.6053.19.1.3.11.1.30739.6
    trapSystemManagementModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 6}

-- 1.3.6.1.4.1.3902.6053.19.1.3.11.1.30739.7
    trapSystemBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 7}

-- 1.3.6.1.4.1.3902.6053.19.1.3.11.1.30739.8
    trapMemoryCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 8}

-- 1.3.6.1.4.1.3902.6053.19.1.3.11.1.30739.9
    trapProcessorModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 9}

-- 1.3.6.1.4.1.3902.6053.19.1.3.11.1.30739.10
    trapPowerSupplyCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 10}

-- 1.3.6.1.4.1.3902.6053.19.1.3.11.1.30739.11
    trapADDINCardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 11}

-- 1.3.6.1.4.1.3902.6053.19.1.3.11.1.30739.12
    trapFrontPanelBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 12}

-- 1.3.6.1.4.1.3902.6053.19.1.3.11.1.30739.13
    trapBackPanelBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 13}

-- 1.3.6.1.4.1.3902.6053.19.1.3.11.1.30739.14
    trapPowerSystemBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 14}

-- 1.3.6.1.4.1.3902.6053.19.1.3.11.1.30739.15
    trapDriveBackplaneCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 15}

-- 1.3.6.1.4.1.3902.6053.19.1.3.11.1.30739.16
    trapSystemInternalExpansionBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 16}

-- 1.3.6.1.4.1.3902.6053.19.1.3.11.1.30739.17
    trapOtherSystemBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 17}

-- 1.3.6.1.4.1.3902.6053.19.1.3.11.1.30739.18
    trapProcessorBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 18}

-- 1.3.6.1.4.1.3902.6053.19.1.3.11.1.30739.19
    trapPowerUnitCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 19}

-- 1.3.6.1.4.1.3902.6053.19.1.3.11.1.30739.20
    trapPowerModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 20}

-- 1.3.6.1.4.1.3902.6053.19.1.3.11.1.30739.21
    trapPowerManagementBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 21}

-- 1.3.6.1.4.1.3902.6053.19.1.3.11.1.30739.22
    trapChassisBackPanelBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 22}

-- 1.3.6.1.4.1.3902.6053.19.1.3.11.1.30739.23
    trapSystemChassisCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 23}

-- 1.3.6.1.4.1.3902.6053.19.1.3.11.1.30739.24
    trapSUBChassisCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 24}

-- 1.3.6.1.4.1.3902.6053.19.1.3.11.1.30739.25
    trapOtherChassisBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 25}

-- 1.3.6.1.4.1.3902.6053.19.1.3.11.1.30739.26
    trapDiskDriveCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 26}

-- 1.3.6.1.4.1.3902.6053.19.1.3.11.1.30739.27
    trapPeripheralBayCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 27}

-- 1.3.6.1.4.1.3902.6053.19.1.3.11.1.30739.28
    trapDeviceBayCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 28}

-- 1.3.6.1.4.1.3902.6053.19.1.3.11.1.30739.29
    trapFanCoolingCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 29}

-- 1.3.6.1.4.1.3902.6053.19.1.3.11.1.30739.30
    trapCoolingUnitCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 30}

-- 1.3.6.1.4.1.3902.6053.19.1.3.11.1.30739.31
    trapCableInterconnectCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 31}

-- 1.3.6.1.4.1.3902.6053.19.1.3.11.1.30739.32
    trapMemoryDeviceCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 32}

-- 1.3.6.1.4.1.3902.6053.19.1.3.11.1.30739.33
    trapSystemManagementSoftwareCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 33}

-- 1.3.6.1.4.1.3902.6053.19.1.3.11.1.30739.34
    trapBiosCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 34}

-- 1.3.6.1.4.1.3902.6053.19.1.3.11.1.30739.35
    trapOperatingSystemCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 35}

-- 1.3.6.1.4.1.3902.6053.19.1.3.11.1.30739.36
    trapSystemBusCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 36}

-- 1.3.6.1.4.1.3902.6053.19.1.3.11.1.30739.37
    trapGroupCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 37}

-- 1.3.6.1.4.1.3902.6053.19.1.3.11.1.30739.38
    trapRemotManagementDeviceCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 38}

-- 1.3.6.1.4.1.3902.6053.19.1.3.11.1.30739.39
    trapExternalEnvironmentCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 39}

-- 1.3.6.1.4.1.3902.6053.19.1.3.11.1.30739.40
    trapBatteryCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 40}

-- 1.3.6.1.4.1.3902.6053.19.1.3.11.1.30739.41
    trapProcessBladeModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 41}

-- 1.3.6.1.4.1.3902.6053.19.1.3.11.1.30739.42
    trapConnectivitySwitchCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 42}

-- 1.3.6.1.4.1.3902.6053.19.1.3.11.1.30739.43
    trapProcessorMemoryModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 43}

-- 1.3.6.1.4.1.3902.6053.19.1.3.11.1.30739.44
    trapIOModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 44}

-- 1.3.6.1.4.1.3902.6053.19.1.3.11.1.30739.45
    trapProcessorIOModuleCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 45}

-- 1.3.6.1.4.1.3902.6053.19.1.3.11.1.30739.46
    trapMGMTControllerFirmwareCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 46}

-- 1.3.6.1.4.1.3902.6053.19.1.3.11.1.30739.47
    trapIPMIChannelCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 47}

-- 1.3.6.1.4.1.3902.6053.19.1.3.11.1.30739.48
    trapPCIBUSCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 48}

-- 1.3.6.1.4.1.3902.6053.19.1.3.11.1.30739.49
    trapPCIExpressBUSCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 49}

-- 1.3.6.1.4.1.3902.6053.19.1.3.11.1.30739.50
    trapSCSIBUSCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 50}

-- 1.3.6.1.4.1.3902.6053.19.1.3.11.1.30739.51
    trapSATASASBUSCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 51}

-- 1.3.6.1.4.1.3902.6053.19.1.3.11.1.30739.52
    trapProcessorFrontSideBUSCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 52}

-- 1.3.6.1.4.1.3902.6053.19.1.3.11.1.30739.53
    trapRealTimeClockCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 53}

-- 1.3.6.1.4.1.3902.6053.19.1.3.11.1.30739.54
    trapSystemFirmwareCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 54}

-- 1.3.6.1.4.1.3902.6053.19.1.3.11.1.30739.160
    trapMainBoardCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 160}

-- 1.3.6.1.4.1.3902.6053.19.1.3.11.1.30739.208
    trapNetPortCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 208}

-- 1.3.6.1.4.1.3902.6053.19.1.3.11.1.30739.209
    trapLogicalDiskCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 209}

-- 1.3.6.1.4.1.3902.6053.19.1.3.11.1.30739.210
    trapStorageCTRLCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 210}

-- 1.3.6.1.4.1.3902.6053.19.1.3.11.1.30739.272
    trapNICSFPCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 272}

-- 1.3.6.1.4.1.3902.6053.19.1.3.11.1.30739.273
    trapOCPSFPCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 273}

-- 1.3.6.1.4.1.3902.6053.19.1.3.11.1.30739.275
    trapSNICSFPCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 28}

-- 1.3.6.1.4.1.3902.6053.19.1.3.11.1.30739.277
    trapDPUT100CurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 277}

-- 1.3.6.1.4.1.3902.6053.19.1.3.11.1.30739.278
    trapDPUT200CurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 278}

-- 1.3.6.1.4.1.3902.6053.19.1.3.11.1.30739.279
    trapBSC25GCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 279}

-- 1.3.6.1.4.1.3902.6053.19.1.3.11.1.30739.281
    trapNEOCurrentIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30739-ucFruId, trap-30739-aucCurrentValue, trap-30739-aucThresholdValue, trap-30739-aucUnitStr, trap-30739-aucSensorName, acTrapTime, acTrapEventSubject, acTrapSeverity, acTrapDescription, acTrapProductSerial, acTrapState, acTrapDeviceSN, acTrapAddInform, dwTrapIndex
		                                        }
		STATUS			current
		DESCRIPTION		"Current is lower than lower-non-critical threshold."
		::=  {  trap-30739-reasoninfo 281}

-- 1.3.6.1.4.1.3902.6053.19.1.3.11.1.30740
    trap-30740-addinfo OBJECT IDENTIFIER ::= {trap-addinfo 30740}

-- 1.3.6.1.4.1.3902.6053.19.1.3.11.2.30740.1
    trap-30740-ucFruId OBJECT-TYPE
        SYNTAX Unsigned32
        ACCESS accessible-for-notify
        STATUS current
        DESCRIPTION 
            "FRU ID"
        ::= {trap-30740-addinfo 1}

-- 1.3.6.1.4.1.3902.6053.19.1.3.11.2.30740.5
    trap-30740-aucCurrentValue OBJECT-TYPE
        SYNTAX DisplayString
        ACCESS accessible-for-notify
        STATUS current
        DESCRIPTION 
            "Current value"
        ::= {trap-30740-addinfo 5}

-- 1.3.6.1.4.1.3902.6053.19.1.3.11.2.30740.6
    trap-30740-aucThresholdValue OBJECT-TYPE
        SYNTAX DisplayString
        ACCESS accessible-for-notify
        STATUS current
        DESCRIPTION 
            "Threshold value"
        ::= {trap-30740-addinfo 6}

-- 1.3.6.1.4.1.3902.6053.19.1.3.11.2.30740.7
    trap-30740-aucUnitStr OBJECT-TYPE
        SYNTAX DisplayString
        ACCESS accessible-for-notify
        STATUS current
        DESCRIPTION 
            "Unit"
        ::= {trap-30740-addinfo 7}

-- 1.3.6.1.4.1.3902.6053.19.1.3.11.2.30740.8
    trap-30740-aucSensorName OBJECT-TYPE
        SYNTAX DisplayString
        ACCESS accessible-for-notify
        STATUS current
        DESCRIPTION 
            "Sensor name"
        ::= {trap-30740-addinfo 8}

-- 1.3.6.1.4.1.3902.6053.19.1.3.11.1.30740
    trapCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-alarm 30740}

-- 1.3.6.1.4.1.3902.6053.19.1.3.11.1.30740
    trap-30740-reasoninfo OBJECT IDENTIFIER ::= {trap-alarm 30740}

-- 1.3.6.1.4.1.3902.6053.19.1.3.11.1.30740.0
    trapUnspecifiedCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 0}

-- 1.3.6.1.4.1.3902.6053.19.1.3.11.1.30740.1
    trapOtherCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 1}

-- 1.3.6.1.4.1.3902.6053.19.1.3.11.1.30740.2
    trapUnkownCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 2}

-- 1.3.6.1.4.1.3902.6053.19.1.3.11.1.30740.3
    trapProcessorCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 3}

-- 1.3.6.1.4.1.3902.6053.19.1.3.11.1.30740.4
    trapDiskCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 4}

-- 1.3.6.1.4.1.3902.6053.19.1.3.11.1.30740.5
    trapPeripheralCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 5}

-- 1.3.6.1.4.1.3902.6053.19.1.3.11.1.30740.6
    trapSystemManagementModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 6}

-- 1.3.6.1.4.1.3902.6053.19.1.3.11.1.30740.7
    trapSystemBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 7}

-- 1.3.6.1.4.1.3902.6053.19.1.3.11.1.30740.8
    trapMemoryCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 8}

-- 1.3.6.1.4.1.3902.6053.19.1.3.11.1.30740.9
    trapProcessorModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 9}

-- 1.3.6.1.4.1.3902.6053.19.1.3.11.1.30740.10
    trapPowerSupplyCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 10}

-- 1.3.6.1.4.1.3902.6053.19.1.3.11.1.30740.11
    trapADDINCardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 11}

-- 1.3.6.1.4.1.3902.6053.19.1.3.11.1.30740.12
    trapFrontPanelBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 12}

-- 1.3.6.1.4.1.3902.6053.19.1.3.11.1.30740.13
    trapBackPanelBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 13}

-- 1.3.6.1.4.1.3902.6053.19.1.3.11.1.30740.14
    trapPowerSystemBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 14}

-- 1.3.6.1.4.1.3902.6053.19.1.3.11.1.30740.15
    trapDriveBackplaneCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 15}

-- 1.3.6.1.4.1.3902.6053.19.1.3.11.1.30740.16
    trapSystemInternalExpansionBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 16}

-- 1.3.6.1.4.1.3902.6053.19.1.3.11.1.30740.17
    trapOtherSystemBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 17}

-- 1.3.6.1.4.1.3902.6053.19.1.3.11.1.30740.18
    trapProcessorBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 18}

-- 1.3.6.1.4.1.3902.6053.19.1.3.11.1.30740.19
    trapPowerUnitCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 19}

-- 1.3.6.1.4.1.3902.6053.19.1.3.11.1.30740.20
    trapPowerModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 20}

-- 1.3.6.1.4.1.3902.6053.19.1.3.11.1.30740.21
    trapPowerManagementBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 21}

-- 1.3.6.1.4.1.3902.6053.19.1.3.11.1.30740.22
    trapChassisBackPanelBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 22}

-- 1.3.6.1.4.1.3902.6053.19.1.3.11.1.30740.23
    trapSystemChassisCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 23}

-- 1.3.6.1.4.1.3902.6053.19.1.3.11.1.30740.24
    trapSUBChassisCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 24}

-- 1.3.6.1.4.1.3902.6053.19.1.3.11.1.30740.25
    trapOtherChassisBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 25}

-- 1.3.6.1.4.1.3902.6053.19.1.3.11.1.30740.26
    trapDiskDriveCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 26}

-- 1.3.6.1.4.1.3902.6053.19.1.3.11.1.30740.27
    trapPeripheralBayCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 27}

-- 1.3.6.1.4.1.3902.6053.19.1.3.11.1.30740.28
    trapDeviceBayCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 28}

-- 1.3.6.1.4.1.3902.6053.19.1.3.11.1.30740.29
    trapFanCoolingCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 29}

-- 1.3.6.1.4.1.3902.6053.19.1.3.11.1.30740.30
    trapCoolingUnitCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 30}

-- 1.3.6.1.4.1.3902.6053.19.1.3.11.1.30740.31
    trapCableInterconnectCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 31}

-- 1.3.6.1.4.1.3902.6053.19.1.3.11.1.30740.32
    trapMemoryDeviceCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 32}

-- 1.3.6.1.4.1.3902.6053.19.1.3.11.1.30740.33
    trapSystemManagementSoftwareCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 33}

-- 1.3.6.1.4.1.3902.6053.19.1.3.11.1.30740.34
    trapBiosCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 34}

-- 1.3.6.1.4.1.3902.6053.19.1.3.11.1.30740.35
    trapOperatingSystemCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 35}

-- 1.3.6.1.4.1.3902.6053.19.1.3.11.1.30740.36
    trapSystemBusCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 36}

-- 1.3.6.1.4.1.3902.6053.19.1.3.11.1.30740.37
    trapGroupCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 37}

-- 1.3.6.1.4.1.3902.6053.19.1.3.11.1.30740.38
    trapRemotManagementDeviceCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 38}

-- 1.3.6.1.4.1.3902.6053.19.1.3.11.1.30740.39
    trapExternalEnvironmentCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 39}

-- 1.3.6.1.4.1.3902.6053.19.1.3.11.1.30740.40
    trapBatteryCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 40}

-- 1.3.6.1.4.1.3902.6053.19.1.3.11.1.30740.41
    trapProcessBladeModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 41}

-- 1.3.6.1.4.1.3902.6053.19.1.3.11.1.30740.42
    trapConnectivitySwitchCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 42}

-- 1.3.6.1.4.1.3902.6053.19.1.3.11.1.30740.43
    trapProcessorMemoryModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 43}

-- 1.3.6.1.4.1.3902.6053.19.1.3.11.1.30740.44
    trapIOModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 44}

-- 1.3.6.1.4.1.3902.6053.19.1.3.11.1.30740.45
    trapProcessorIOModuleCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 45}

-- 1.3.6.1.4.1.3902.6053.19.1.3.11.1.30740.46
    trapMGMTControllerFirmwareCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 46}

-- 1.3.6.1.4.1.3902.6053.19.1.3.11.1.30740.47
    trapIPMIChannelCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 47}

-- 1.3.6.1.4.1.3902.6053.19.1.3.11.1.30740.48
    trapPCIBUSCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 48}

-- 1.3.6.1.4.1.3902.6053.19.1.3.11.1.30740.49
    trapPCIExpressBUSCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 49}

-- 1.3.6.1.4.1.3902.6053.19.1.3.11.1.30740.50
    trapSCSIBUSCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 50}

-- 1.3.6.1.4.1.3902.6053.19.1.3.11.1.30740.51
    trapSATASASBUSCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 51}

-- 1.3.6.1.4.1.3902.6053.19.1.3.11.1.30740.52
    trapProcessorFrontSideBUSCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 52}

-- 1.3.6.1.4.1.3902.6053.19.1.3.11.1.30740.53
    trapRealTimeClockCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 53}

-- 1.3.6.1.4.1.3902.6053.19.1.3.11.1.30740.54
    trapSystemFirmwareCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 54}

-- 1.3.6.1.4.1.3902.6053.19.1.3.11.1.30740.160
    trapMainBoardCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 160}

-- 1.3.6.1.4.1.3902.6053.19.1.3.11.1.30740.208
    trapNetPortCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 208}

-- 1.3.6.1.4.1.3902.6053.19.1.3.11.1.30740.209
    trapLogicalDiskCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 209}

-- 1.3.6.1.4.1.3902.6053.19.1.3.11.1.30740.210
    trapStorageCTRLCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 210}

-- 1.3.6.1.4.1.3902.6053.19.1.3.11.1.30740.272
    trapNICSFPCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 272}

-- 1.3.6.1.4.1.3902.6053.19.1.3.11.1.30740.273
    trapOCPSFPCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 273}

-- 1.3.6.1.4.1.3902.6053.19.1.3.11.1.30740.275
    trapSNICSFPCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 28}

-- 1.3.6.1.4.1.3902.6053.19.1.3.11.1.30740.277
    trapDPUT100CurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 277}

-- 1.3.6.1.4.1.3902.6053.19.1.3.11.1.30740.278
    trapDPUT200CurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 278}

-- 1.3.6.1.4.1.3902.6053.19.1.3.11.1.30740.279
    trapBSC25GCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 279}

-- 1.3.6.1.4.1.3902.6053.19.1.3.11.1.30740.281
    trapNEOCurrentIsLowerThanLowerCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30740-ucFruId, trap-30740-aucCurrentValue, trap-30740-aucThresholdValue, trap-30740-aucUnitStr, trap-30740-aucSensorName, acTrapTime, acTrapEventSubject, acTrapSeverity, acTrapDescription, acTrapProductSerial, acTrapState, acTrapDeviceSN, acTrapAddInform, dwTrapIndex
		                                        }
		STATUS			current
		DESCRIPTION		"Current is lower than lower-critical threshold."
		::=  {  trap-30740-reasoninfo 281}

-- 1.3.6.1.4.1.3902.6053.19.1.3.11.1.30741
    trap-30741-addinfo OBJECT IDENTIFIER ::= {trap-addinfo 30741}

-- 1.3.6.1.4.1.3902.6053.19.1.3.11.2.30741.1
    trap-30741-ucFruId OBJECT-TYPE
        SYNTAX Unsigned32
        ACCESS accessible-for-notify
        STATUS current
        DESCRIPTION 
            "FRU ID"
        ::= {trap-30741-addinfo 1}

-- 1.3.6.1.4.1.3902.6053.19.1.3.11.2.30741.5
    trap-30741-aucCurrentValue OBJECT-TYPE
        SYNTAX DisplayString
        ACCESS accessible-for-notify
        STATUS current
        DESCRIPTION 
            "Current value"
        ::= {trap-30741-addinfo 5}

-- 1.3.6.1.4.1.3902.6053.19.1.3.11.2.30741.6
    trap-30741-aucThresholdValue OBJECT-TYPE
        SYNTAX DisplayString
        ACCESS accessible-for-notify
        STATUS current
        DESCRIPTION 
            "Threshold value"
        ::= {trap-30741-addinfo 6}

-- 1.3.6.1.4.1.3902.6053.19.1.3.11.2.30741.7
    trap-30741-aucUnitStr OBJECT-TYPE
        SYNTAX DisplayString
        ACCESS accessible-for-notify
        STATUS current
        DESCRIPTION 
            "Unit"
        ::= {trap-30741-addinfo 7}

-- 1.3.6.1.4.1.3902.6053.19.1.3.11.2.30741.8
    trap-30741-aucSensorName OBJECT-TYPE
        SYNTAX DisplayString
        ACCESS accessible-for-notify
        STATUS current
        DESCRIPTION 
            "Sensor name"
        ::= {trap-30741-addinfo 8}

-- 1.3.6.1.4.1.3902.6053.19.1.3.11.1.30741
    trapCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-alarm 30741}

-- 1.3.6.1.4.1.3902.6053.19.1.3.11.1.30741
    trap-30741-reasoninfo OBJECT IDENTIFIER ::= {trap-alarm 30741}

-- 1.3.6.1.4.1.3902.6053.19.1.3.11.1.30741.0
    trapUnspecifiedCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 0}

-- 1.3.6.1.4.1.3902.6053.19.1.3.11.1.30741.1
    trapOtherCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 1}

-- 1.3.6.1.4.1.3902.6053.19.1.3.11.1.30741.2
    trapUnkownCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 2}

-- 1.3.6.1.4.1.3902.6053.19.1.3.11.1.30741.3
    trapProcessorCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 3}

-- 1.3.6.1.4.1.3902.6053.19.1.3.11.1.30741.4
    trapDiskCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 4}

-- 1.3.6.1.4.1.3902.6053.19.1.3.11.1.30741.5
    trapPeripheralCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 5}

-- 1.3.6.1.4.1.3902.6053.19.1.3.11.1.30741.6
    trapSystemManagementModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 6}

-- 1.3.6.1.4.1.3902.6053.19.1.3.11.1.30741.7
    trapSystemBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 7}

-- 1.3.6.1.4.1.3902.6053.19.1.3.11.1.30741.8
    trapMemoryCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 8}

-- 1.3.6.1.4.1.3902.6053.19.1.3.11.1.30741.9
    trapProcessorModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 9}

-- 1.3.6.1.4.1.3902.6053.19.1.3.11.1.30741.10
    trapPowerSupplyCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 10}

-- 1.3.6.1.4.1.3902.6053.19.1.3.11.1.30741.11
    trapADDINCardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 11}

-- 1.3.6.1.4.1.3902.6053.19.1.3.11.1.30741.12
    trapFrontPanelBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 12}

-- 1.3.6.1.4.1.3902.6053.19.1.3.11.1.30741.13
    trapBackPanelBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 13}

-- 1.3.6.1.4.1.3902.6053.19.1.3.11.1.30741.14
    trapPowerSystemBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 14}

-- 1.3.6.1.4.1.3902.6053.19.1.3.11.1.30741.15
    trapDriveBackplaneCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 15}

-- 1.3.6.1.4.1.3902.6053.19.1.3.11.1.30741.16
    trapSystemInternalExpansionBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 16}

-- 1.3.6.1.4.1.3902.6053.19.1.3.11.1.30741.17
    trapOtherSystemBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 17}

-- 1.3.6.1.4.1.3902.6053.19.1.3.11.1.30741.18
    trapProcessorBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 18}

-- 1.3.6.1.4.1.3902.6053.19.1.3.11.1.30741.19
    trapPowerUnitCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 19}

-- 1.3.6.1.4.1.3902.6053.19.1.3.11.1.30741.20
    trapPowerModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 20}

-- 1.3.6.1.4.1.3902.6053.19.1.3.11.1.30741.21
    trapPowerManagementBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 21}

-- 1.3.6.1.4.1.3902.6053.19.1.3.11.1.30741.22
    trapChassisBackPanelBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 22}

-- 1.3.6.1.4.1.3902.6053.19.1.3.11.1.30741.23
    trapSystemChassisCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 23}

-- 1.3.6.1.4.1.3902.6053.19.1.3.11.1.30741.24
    trapSUBChassisCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 24}

-- 1.3.6.1.4.1.3902.6053.19.1.3.11.1.30741.25
    trapOtherChassisBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 25}

-- 1.3.6.1.4.1.3902.6053.19.1.3.11.1.30741.26
    trapDiskDriveCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 26}

-- 1.3.6.1.4.1.3902.6053.19.1.3.11.1.30741.27
    trapPeripheralBayCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 27}

-- 1.3.6.1.4.1.3902.6053.19.1.3.11.1.30741.28
    trapDeviceBayCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 28}

-- 1.3.6.1.4.1.3902.6053.19.1.3.11.1.30741.29
    trapFanCoolingCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 29}

-- 1.3.6.1.4.1.3902.6053.19.1.3.11.1.30741.30
    trapCoolingUnitCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 30}

-- 1.3.6.1.4.1.3902.6053.19.1.3.11.1.30741.31
    trapCableInterconnectCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 31}

-- 1.3.6.1.4.1.3902.6053.19.1.3.11.1.30741.32
    trapMemoryDeviceCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 32}

-- 1.3.6.1.4.1.3902.6053.19.1.3.11.1.30741.33
    trapSystemManagementSoftwareCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 33}

-- 1.3.6.1.4.1.3902.6053.19.1.3.11.1.30741.34
    trapBiosCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 34}

-- 1.3.6.1.4.1.3902.6053.19.1.3.11.1.30741.35
    trapOperatingSystemCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 35}

-- 1.3.6.1.4.1.3902.6053.19.1.3.11.1.30741.36
    trapSystemBusCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 36}

-- 1.3.6.1.4.1.3902.6053.19.1.3.11.1.30741.37
    trapGroupCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 37}

-- 1.3.6.1.4.1.3902.6053.19.1.3.11.1.30741.38
    trapRemotManagementDeviceCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 38}

-- 1.3.6.1.4.1.3902.6053.19.1.3.11.1.30741.39
    trapExternalEnvironmentCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 39}

-- 1.3.6.1.4.1.3902.6053.19.1.3.11.1.30741.40
    trapBatteryCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 40}

-- 1.3.6.1.4.1.3902.6053.19.1.3.11.1.30741.41
    trapProcessBladeModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 41}

-- 1.3.6.1.4.1.3902.6053.19.1.3.11.1.30741.42
    trapConnectivitySwitchCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 42}

-- 1.3.6.1.4.1.3902.6053.19.1.3.11.1.30741.43
    trapProcessorMemoryModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 43}

-- 1.3.6.1.4.1.3902.6053.19.1.3.11.1.30741.44
    trapIOModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 44}

-- 1.3.6.1.4.1.3902.6053.19.1.3.11.1.30741.45
    trapProcessorIOModuleCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 45}

-- 1.3.6.1.4.1.3902.6053.19.1.3.11.1.30741.46
    trapMGMTControllerFirmwareCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 46}

-- 1.3.6.1.4.1.3902.6053.19.1.3.11.1.30741.47
    trapIPMIChannelCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 47}

-- 1.3.6.1.4.1.3902.6053.19.1.3.11.1.30741.48
    trapPCIBUSCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 48}

-- 1.3.6.1.4.1.3902.6053.19.1.3.11.1.30741.49
    trapPCIExpressBUSCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 49}

-- 1.3.6.1.4.1.3902.6053.19.1.3.11.1.30741.50
    trapSCSIBUSCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 50}

-- 1.3.6.1.4.1.3902.6053.19.1.3.11.1.30741.51
    trapSATASASBUSCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 51}

-- 1.3.6.1.4.1.3902.6053.19.1.3.11.1.30741.52
    trapProcessorFrontSideBUSCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 52}

-- 1.3.6.1.4.1.3902.6053.19.1.3.11.1.30741.53
    trapRealTimeClockCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 53}

-- 1.3.6.1.4.1.3902.6053.19.1.3.11.1.30741.54
    trapSystemFirmwareCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 54}

-- 1.3.6.1.4.1.3902.6053.19.1.3.11.1.30741.160
    trapMainBoardCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 160}

-- 1.3.6.1.4.1.3902.6053.19.1.3.11.1.30741.208
    trapNetPortCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 208}

-- 1.3.6.1.4.1.3902.6053.19.1.3.11.1.30741.209
    trapLogicalDiskCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 209}

-- 1.3.6.1.4.1.3902.6053.19.1.3.11.1.30741.210
    trapStorageCTRLCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 210}

-- 1.3.6.1.4.1.3902.6053.19.1.3.11.1.30741.272
    trapNICSFPCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 272}

-- 1.3.6.1.4.1.3902.6053.19.1.3.11.1.30741.273
    trapOCPSFPCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 273}

-- 1.3.6.1.4.1.3902.6053.19.1.3.11.1.30741.275
    trapSNICSFPCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 28}

-- 1.3.6.1.4.1.3902.6053.19.1.3.11.1.30741.277
    trapDPUT100CurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 277}

-- 1.3.6.1.4.1.3902.6053.19.1.3.11.1.30741.278
    trapDPUT200CurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 278}

-- 1.3.6.1.4.1.3902.6053.19.1.3.11.1.30741.279
    trapBSC25GCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 279}

-- 1.3.6.1.4.1.3902.6053.19.1.3.11.1.30741.281
    trapNEOCurrentIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30741-ucFruId, trap-30741-aucCurrentValue, trap-30741-aucThresholdValue, trap-30741-aucUnitStr, trap-30741-aucSensorName, acTrapTime, acTrapEventSubject, acTrapSeverity, acTrapDescription, acTrapProductSerial, acTrapState, acTrapDeviceSN, acTrapAddInform, dwTrapIndex
		                                        }
		STATUS			current
		DESCRIPTION		"Current is lower than lower-non-recoverable threshold."
		::=  {  trap-30741-reasoninfo 281}

-- 1.3.6.1.4.1.3902.6053.19.1.3.11.1.30742
    trap-30742-addinfo OBJECT IDENTIFIER ::= {trap-addinfo 30742}

-- 1.3.6.1.4.1.3902.6053.19.1.3.11.2.30742.1
    trap-30742-ucFruId OBJECT-TYPE
        SYNTAX Unsigned32
        ACCESS accessible-for-notify
        STATUS current
        DESCRIPTION 
            "FRU ID"
        ::= {trap-30742-addinfo 1}

-- 1.3.6.1.4.1.3902.6053.19.1.3.11.2.30742.5
    trap-30742-aucCurrentValue OBJECT-TYPE
        SYNTAX DisplayString
        ACCESS accessible-for-notify
        STATUS current
        DESCRIPTION 
            "Current value"
        ::= {trap-30742-addinfo 5}

-- 1.3.6.1.4.1.3902.6053.19.1.3.11.2.30742.6
    trap-30742-aucThresholdValue OBJECT-TYPE
        SYNTAX DisplayString
        ACCESS accessible-for-notify
        STATUS current
        DESCRIPTION 
            "Threshold value"
        ::= {trap-30742-addinfo 6}

-- 1.3.6.1.4.1.3902.6053.19.1.3.11.2.30742.7
    trap-30742-aucUnitStr OBJECT-TYPE
        SYNTAX DisplayString
        ACCESS accessible-for-notify
        STATUS current
        DESCRIPTION 
            "Unit"
        ::= {trap-30742-addinfo 7}

-- 1.3.6.1.4.1.3902.6053.19.1.3.11.2.30742.8
    trap-30742-aucSensorName OBJECT-TYPE
        SYNTAX DisplayString
        ACCESS accessible-for-notify
        STATUS current
        DESCRIPTION 
            "Sensor name"
        ::= {trap-30742-addinfo 8}

-- 1.3.6.1.4.1.3902.6053.19.1.3.11.1.30742
    trapCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-alarm 30742}

-- 1.3.6.1.4.1.3902.6053.19.1.3.11.1.30742
    trap-30742-reasoninfo OBJECT IDENTIFIER ::= {trap-alarm 30742}

-- 1.3.6.1.4.1.3902.6053.19.1.3.11.1.30742.0
    trapUnspecifiedCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 0}

-- 1.3.6.1.4.1.3902.6053.19.1.3.11.1.30742.1
    trapOtherCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 1}

-- 1.3.6.1.4.1.3902.6053.19.1.3.11.1.30742.2
    trapUnkownCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 2}

-- 1.3.6.1.4.1.3902.6053.19.1.3.11.1.30742.3
    trapProcessorCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 3}

-- 1.3.6.1.4.1.3902.6053.19.1.3.11.1.30742.4
    trapDiskCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 4}

-- 1.3.6.1.4.1.3902.6053.19.1.3.11.1.30742.5
    trapPeripheralCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 5}

-- 1.3.6.1.4.1.3902.6053.19.1.3.11.1.30742.6
    trapSystemManagementModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 6}

-- 1.3.6.1.4.1.3902.6053.19.1.3.11.1.30742.7
    trapSystemBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 7}

-- 1.3.6.1.4.1.3902.6053.19.1.3.11.1.30742.8
    trapMemoryCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 8}

-- 1.3.6.1.4.1.3902.6053.19.1.3.11.1.30742.9
    trapProcessorModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 9}

-- 1.3.6.1.4.1.3902.6053.19.1.3.11.1.30742.10
    trapPowerSupplyCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 10}

-- 1.3.6.1.4.1.3902.6053.19.1.3.11.1.30742.11
    trapADDINCardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 11}

-- 1.3.6.1.4.1.3902.6053.19.1.3.11.1.30742.12
    trapFrontPanelBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 12}

-- 1.3.6.1.4.1.3902.6053.19.1.3.11.1.30742.13
    trapBackPanelBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 13}

-- 1.3.6.1.4.1.3902.6053.19.1.3.11.1.30742.14
    trapPowerSystemBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 14}

-- 1.3.6.1.4.1.3902.6053.19.1.3.11.1.30742.15
    trapDriveBackplaneCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 15}

-- 1.3.6.1.4.1.3902.6053.19.1.3.11.1.30742.16
    trapSystemInternalExpansionBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 16}

-- 1.3.6.1.4.1.3902.6053.19.1.3.11.1.30742.17
    trapOtherSystemBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 17}

-- 1.3.6.1.4.1.3902.6053.19.1.3.11.1.30742.18
    trapProcessorBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 18}

-- 1.3.6.1.4.1.3902.6053.19.1.3.11.1.30742.19
    trapPowerUnitCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 19}

-- 1.3.6.1.4.1.3902.6053.19.1.3.11.1.30742.20
    trapPowerModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 20}

-- 1.3.6.1.4.1.3902.6053.19.1.3.11.1.30742.21
    trapPowerManagementBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 21}

-- 1.3.6.1.4.1.3902.6053.19.1.3.11.1.30742.22
    trapChassisBackPanelBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 22}

-- 1.3.6.1.4.1.3902.6053.19.1.3.11.1.30742.23
    trapSystemChassisCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 23}

-- 1.3.6.1.4.1.3902.6053.19.1.3.11.1.30742.24
    trapSUBChassisCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 24}

-- 1.3.6.1.4.1.3902.6053.19.1.3.11.1.30742.25
    trapOtherChassisBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 25}

-- 1.3.6.1.4.1.3902.6053.19.1.3.11.1.30742.26
    trapDiskDriveCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 26}

-- 1.3.6.1.4.1.3902.6053.19.1.3.11.1.30742.27
    trapPeripheralBayCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 27}

-- 1.3.6.1.4.1.3902.6053.19.1.3.11.1.30742.28
    trapDeviceBayCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 28}

-- 1.3.6.1.4.1.3902.6053.19.1.3.11.1.30742.29
    trapFanCoolingCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 29}

-- 1.3.6.1.4.1.3902.6053.19.1.3.11.1.30742.30
    trapCoolingUnitCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 30}

-- 1.3.6.1.4.1.3902.6053.19.1.3.11.1.30742.31
    trapCableInterconnectCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 31}

-- 1.3.6.1.4.1.3902.6053.19.1.3.11.1.30742.32
    trapMemoryDeviceCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 32}

-- 1.3.6.1.4.1.3902.6053.19.1.3.11.1.30742.33
    trapSystemManagementSoftwareCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 33}

-- 1.3.6.1.4.1.3902.6053.19.1.3.11.1.30742.34
    trapBiosCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 34}

-- 1.3.6.1.4.1.3902.6053.19.1.3.11.1.30742.35
    trapOperatingSystemCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 35}

-- 1.3.6.1.4.1.3902.6053.19.1.3.11.1.30742.36
    trapSystemBusCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 36}

-- 1.3.6.1.4.1.3902.6053.19.1.3.11.1.30742.37
    trapGroupCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 37}

-- 1.3.6.1.4.1.3902.6053.19.1.3.11.1.30742.38
    trapRemotManagementDeviceCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 38}

-- 1.3.6.1.4.1.3902.6053.19.1.3.11.1.30742.39
    trapExternalEnvironmentCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 39}

-- 1.3.6.1.4.1.3902.6053.19.1.3.11.1.30742.40
    trapBatteryCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 40}

-- 1.3.6.1.4.1.3902.6053.19.1.3.11.1.30742.41
    trapProcessBladeModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 41}

-- 1.3.6.1.4.1.3902.6053.19.1.3.11.1.30742.42
    trapConnectivitySwitchCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 42}

-- 1.3.6.1.4.1.3902.6053.19.1.3.11.1.30742.43
    trapProcessorMemoryModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 43}

-- 1.3.6.1.4.1.3902.6053.19.1.3.11.1.30742.44
    trapIOModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 44}

-- 1.3.6.1.4.1.3902.6053.19.1.3.11.1.30742.45
    trapProcessorIOModuleCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 45}

-- 1.3.6.1.4.1.3902.6053.19.1.3.11.1.30742.46
    trapMGMTControllerFirmwareCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 46}

-- 1.3.6.1.4.1.3902.6053.19.1.3.11.1.30742.47
    trapIPMIChannelCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 47}

-- 1.3.6.1.4.1.3902.6053.19.1.3.11.1.30742.48
    trapPCIBUSCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 48}

-- 1.3.6.1.4.1.3902.6053.19.1.3.11.1.30742.49
    trapPCIExpressBUSCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 49}

-- 1.3.6.1.4.1.3902.6053.19.1.3.11.1.30742.50
    trapSCSIBUSCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 50}

-- 1.3.6.1.4.1.3902.6053.19.1.3.11.1.30742.51
    trapSATASASBUSCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 51}

-- 1.3.6.1.4.1.3902.6053.19.1.3.11.1.30742.52
    trapProcessorFrontSideBUSCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 52}

-- 1.3.6.1.4.1.3902.6053.19.1.3.11.1.30742.53
    trapRealTimeClockCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 53}

-- 1.3.6.1.4.1.3902.6053.19.1.3.11.1.30742.54
    trapSystemFirmwareCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 54}

-- 1.3.6.1.4.1.3902.6053.19.1.3.11.1.30742.160
    trapMainBoardCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 160}

-- 1.3.6.1.4.1.3902.6053.19.1.3.11.1.30742.208
    trapNetPortCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 208}

-- 1.3.6.1.4.1.3902.6053.19.1.3.11.1.30742.209
    trapLogicalDiskCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 209}

-- 1.3.6.1.4.1.3902.6053.19.1.3.11.1.30742.210
    trapStorageCTRLCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 210}

-- 1.3.6.1.4.1.3902.6053.19.1.3.11.1.30742.272
    trapNICSFPCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 272}

-- 1.3.6.1.4.1.3902.6053.19.1.3.11.1.30742.273
    trapOCPSFPCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 273}

-- 1.3.6.1.4.1.3902.6053.19.1.3.11.1.30742.275
    trapSNICSFPCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 28}

-- 1.3.6.1.4.1.3902.6053.19.1.3.11.1.30742.277
    trapDPUT100CurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 277}

-- 1.3.6.1.4.1.3902.6053.19.1.3.11.1.30742.278
    trapDPUT200CurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 278}

-- 1.3.6.1.4.1.3902.6053.19.1.3.11.1.30742.279
    trapBSC25GCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 279}

-- 1.3.6.1.4.1.3902.6053.19.1.3.11.1.30742.281
    trapNEOCurrentIsHigherThanUpperNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30742-ucFruId, trap-30742-aucCurrentValue, trap-30742-aucThresholdValue, trap-30742-aucUnitStr, trap-30742-aucSensorName, acTrapTime, acTrapEventSubject, acTrapSeverity, acTrapDescription, acTrapProductSerial, acTrapState, acTrapDeviceSN, acTrapAddInform, dwTrapIndex
		                                        }
		STATUS			current
		DESCRIPTION		"Current is higher than upper-non-critical threshold."
		::=  {  trap-30742-reasoninfo 281}

-- 1.3.6.1.4.1.3902.6053.19.1.3.11.1.30743
    trap-30743-addinfo OBJECT IDENTIFIER ::= {trap-addinfo 30743}

-- 1.3.6.1.4.1.3902.6053.19.1.3.11.2.30743.1
    trap-30743-ucFruId OBJECT-TYPE
        SYNTAX Unsigned32
        ACCESS accessible-for-notify
        STATUS current
        DESCRIPTION 
            "FRU ID"
        ::= {trap-30743-addinfo 1}

-- 1.3.6.1.4.1.3902.6053.19.1.3.11.2.30743.5
    trap-30743-aucCurrentValue OBJECT-TYPE
        SYNTAX DisplayString
        ACCESS accessible-for-notify
        STATUS current
        DESCRIPTION 
            "Current value"
        ::= {trap-30743-addinfo 5}

-- 1.3.6.1.4.1.3902.6053.19.1.3.11.2.30743.6
    trap-30743-aucThresholdValue OBJECT-TYPE
        SYNTAX DisplayString
        ACCESS accessible-for-notify
        STATUS current
        DESCRIPTION 
            "Threshold value"
        ::= {trap-30743-addinfo 6}

-- 1.3.6.1.4.1.3902.6053.19.1.3.11.2.30743.7
    trap-30743-aucUnitStr OBJECT-TYPE
        SYNTAX DisplayString
        ACCESS accessible-for-notify
        STATUS current
        DESCRIPTION 
            "Unit"
        ::= {trap-30743-addinfo 7}

-- 1.3.6.1.4.1.3902.6053.19.1.3.11.2.30743.8
    trap-30743-aucSensorName OBJECT-TYPE
        SYNTAX DisplayString
        ACCESS accessible-for-notify
        STATUS current
        DESCRIPTION 
            "Sensor name"
        ::= {trap-30743-addinfo 8}

-- 1.3.6.1.4.1.3902.6053.19.1.3.11.1.30743
    trapCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-alarm 30743}

-- 1.3.6.1.4.1.3902.6053.19.1.3.11.1.30743
    trap-30743-reasoninfo OBJECT IDENTIFIER ::= {trap-alarm 30743}

-- 1.3.6.1.4.1.3902.6053.19.1.3.11.1.30743.0
    trapUnspecifiedCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 0}

-- 1.3.6.1.4.1.3902.6053.19.1.3.11.1.30743.1
    trapOtherCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 1}

-- 1.3.6.1.4.1.3902.6053.19.1.3.11.1.30743.2
    trapUnkownCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 2}

-- 1.3.6.1.4.1.3902.6053.19.1.3.11.1.30743.3
    trapProcessorCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 3}

-- 1.3.6.1.4.1.3902.6053.19.1.3.11.1.30743.4
    trapDiskCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 4}

-- 1.3.6.1.4.1.3902.6053.19.1.3.11.1.30743.5
    trapPeripheralCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 5}

-- 1.3.6.1.4.1.3902.6053.19.1.3.11.1.30743.6
    trapSystemManagementModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 6}

-- 1.3.6.1.4.1.3902.6053.19.1.3.11.1.30743.7
    trapSystemBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 7}

-- 1.3.6.1.4.1.3902.6053.19.1.3.11.1.30743.8
    trapMemoryCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 8}

-- 1.3.6.1.4.1.3902.6053.19.1.3.11.1.30743.9
    trapProcessorModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 9}

-- 1.3.6.1.4.1.3902.6053.19.1.3.11.1.30743.10
    trapPowerSupplyCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 10}

-- 1.3.6.1.4.1.3902.6053.19.1.3.11.1.30743.11
    trapADDINCardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 11}

-- 1.3.6.1.4.1.3902.6053.19.1.3.11.1.30743.12
    trapFrontPanelBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 12}

-- 1.3.6.1.4.1.3902.6053.19.1.3.11.1.30743.13
    trapBackPanelBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 13}

-- 1.3.6.1.4.1.3902.6053.19.1.3.11.1.30743.14
    trapPowerSystemBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 14}

-- 1.3.6.1.4.1.3902.6053.19.1.3.11.1.30743.15
    trapDriveBackplaneCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 15}

-- 1.3.6.1.4.1.3902.6053.19.1.3.11.1.30743.16
    trapSystemInternalExpansionBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 16}

-- 1.3.6.1.4.1.3902.6053.19.1.3.11.1.30743.17
    trapOtherSystemBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 17}

-- 1.3.6.1.4.1.3902.6053.19.1.3.11.1.30743.18
    trapProcessorBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 18}

-- 1.3.6.1.4.1.3902.6053.19.1.3.11.1.30743.19
    trapPowerUnitCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 19}

-- 1.3.6.1.4.1.3902.6053.19.1.3.11.1.30743.20
    trapPowerModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 20}

-- 1.3.6.1.4.1.3902.6053.19.1.3.11.1.30743.21
    trapPowerManagementBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 21}

-- 1.3.6.1.4.1.3902.6053.19.1.3.11.1.30743.22
    trapChassisBackPanelBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 22}

-- 1.3.6.1.4.1.3902.6053.19.1.3.11.1.30743.23
    trapSystemChassisCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 23}

-- 1.3.6.1.4.1.3902.6053.19.1.3.11.1.30743.24
    trapSUBChassisCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 24}

-- 1.3.6.1.4.1.3902.6053.19.1.3.11.1.30743.25
    trapOtherChassisBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 25}

-- 1.3.6.1.4.1.3902.6053.19.1.3.11.1.30743.26
    trapDiskDriveCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 26}

-- 1.3.6.1.4.1.3902.6053.19.1.3.11.1.30743.27
    trapPeripheralBayCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 27}

-- 1.3.6.1.4.1.3902.6053.19.1.3.11.1.30743.28
    trapDeviceBayCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 28}

-- 1.3.6.1.4.1.3902.6053.19.1.3.11.1.30743.29
    trapFanCoolingCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 29}

-- 1.3.6.1.4.1.3902.6053.19.1.3.11.1.30743.30
    trapCoolingUnitCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 30}

-- 1.3.6.1.4.1.3902.6053.19.1.3.11.1.30743.31
    trapCableInterconnectCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 31}

-- 1.3.6.1.4.1.3902.6053.19.1.3.11.1.30743.32
    trapMemoryDeviceCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 32}

-- 1.3.6.1.4.1.3902.6053.19.1.3.11.1.30743.33
    trapSystemManagementSoftwareCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 33}

-- 1.3.6.1.4.1.3902.6053.19.1.3.11.1.30743.34
    trapBiosCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 34}

-- 1.3.6.1.4.1.3902.6053.19.1.3.11.1.30743.35
    trapOperatingSystemCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 35}

-- 1.3.6.1.4.1.3902.6053.19.1.3.11.1.30743.36
    trapSystemBusCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 36}

-- 1.3.6.1.4.1.3902.6053.19.1.3.11.1.30743.37
    trapGroupCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 37}

-- 1.3.6.1.4.1.3902.6053.19.1.3.11.1.30743.38
    trapRemotManagementDeviceCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 38}

-- 1.3.6.1.4.1.3902.6053.19.1.3.11.1.30743.39
    trapExternalEnvironmentCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 39}

-- 1.3.6.1.4.1.3902.6053.19.1.3.11.1.30743.40
    trapBatteryCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 40}

-- 1.3.6.1.4.1.3902.6053.19.1.3.11.1.30743.41
    trapProcessBladeModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 41}

-- 1.3.6.1.4.1.3902.6053.19.1.3.11.1.30743.42
    trapConnectivitySwitchCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 42}

-- 1.3.6.1.4.1.3902.6053.19.1.3.11.1.30743.43
    trapProcessorMemoryModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 43}

-- 1.3.6.1.4.1.3902.6053.19.1.3.11.1.30743.44
    trapIOModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 44}

-- 1.3.6.1.4.1.3902.6053.19.1.3.11.1.30743.45
    trapProcessorIOModuleCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 45}

-- 1.3.6.1.4.1.3902.6053.19.1.3.11.1.30743.46
    trapMGMTControllerFirmwareCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 46}

-- 1.3.6.1.4.1.3902.6053.19.1.3.11.1.30743.47
    trapIPMIChannelCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 47}

-- 1.3.6.1.4.1.3902.6053.19.1.3.11.1.30743.48
    trapPCIBUSCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 48}

-- 1.3.6.1.4.1.3902.6053.19.1.3.11.1.30743.49
    trapPCIExpressBUSCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 49}

-- 1.3.6.1.4.1.3902.6053.19.1.3.11.1.30743.50
    trapSCSIBUSCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 50}

-- 1.3.6.1.4.1.3902.6053.19.1.3.11.1.30743.51
    trapSATASASBUSCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 51}

-- 1.3.6.1.4.1.3902.6053.19.1.3.11.1.30743.52
    trapProcessorFrontSideBUSCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 52}

-- 1.3.6.1.4.1.3902.6053.19.1.3.11.1.30743.53
    trapRealTimeClockCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 53}

-- 1.3.6.1.4.1.3902.6053.19.1.3.11.1.30743.54
    trapSystemFirmwareCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 54}

-- 1.3.6.1.4.1.3902.6053.19.1.3.11.1.30743.160
    trapMainBoardCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 160}

-- 1.3.6.1.4.1.3902.6053.19.1.3.11.1.30743.208
    trapNetPortCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 208}

-- 1.3.6.1.4.1.3902.6053.19.1.3.11.1.30743.209
    trapLogicalDiskCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 209}

-- 1.3.6.1.4.1.3902.6053.19.1.3.11.1.30743.210
    trapStorageCTRLCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 210}

-- 1.3.6.1.4.1.3902.6053.19.1.3.11.1.30743.272
    trapNICSFPCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 272}

-- 1.3.6.1.4.1.3902.6053.19.1.3.11.1.30743.273
    trapOCPSFPCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 273}

-- 1.3.6.1.4.1.3902.6053.19.1.3.11.1.30743.275
    trapSNICSFPCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 28}

-- 1.3.6.1.4.1.3902.6053.19.1.3.11.1.30743.277
    trapDPUT100CurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 277}

-- 1.3.6.1.4.1.3902.6053.19.1.3.11.1.30743.278
    trapDPUT200CurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 278}

-- 1.3.6.1.4.1.3902.6053.19.1.3.11.1.30743.279
    trapBSC25GCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 279}

-- 1.3.6.1.4.1.3902.6053.19.1.3.11.1.30743.281
    trapNEOCurrentIsHigherThanUpperCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30743-ucFruId, trap-30743-aucCurrentValue, trap-30743-aucThresholdValue, trap-30743-aucUnitStr, trap-30743-aucSensorName, acTrapTime, acTrapEventSubject, acTrapSeverity, acTrapDescription, acTrapProductSerial, acTrapState, acTrapDeviceSN, acTrapAddInform, dwTrapIndex
		                                        }
		STATUS			current
		DESCRIPTION		"Current is higher than upper-critical threshold."
		::=  {  trap-30743-reasoninfo 281}

-- 1.3.6.1.4.1.3902.6053.19.1.3.11.1.30744
    trap-30744-addinfo OBJECT IDENTIFIER ::= {trap-addinfo 30744}

-- 1.3.6.1.4.1.3902.6053.19.1.3.11.2.30744.1
    trap-30744-ucFruId OBJECT-TYPE
        SYNTAX Unsigned32
        ACCESS accessible-for-notify
        STATUS current
        DESCRIPTION 
            "FRU ID"
        ::= {trap-30744-addinfo 1}

-- 1.3.6.1.4.1.3902.6053.19.1.3.11.2.30744.5
    trap-30744-aucCurrentValue OBJECT-TYPE
        SYNTAX DisplayString
        ACCESS accessible-for-notify
        STATUS current
        DESCRIPTION 
            "Current value"
        ::= {trap-30744-addinfo 5}

-- 1.3.6.1.4.1.3902.6053.19.1.3.11.2.30744.6
    trap-30744-aucThresholdValue OBJECT-TYPE
        SYNTAX DisplayString
        ACCESS accessible-for-notify
        STATUS current
        DESCRIPTION 
            "Threshold value"
        ::= {trap-30744-addinfo 6}

-- 1.3.6.1.4.1.3902.6053.19.1.3.11.2.30744.7
    trap-30744-aucUnitStr OBJECT-TYPE
        SYNTAX DisplayString
        ACCESS accessible-for-notify
        STATUS current
        DESCRIPTION 
            "Unit"
        ::= {trap-30744-addinfo 7}

-- 1.3.6.1.4.1.3902.6053.19.1.3.11.2.30744.8
    trap-30744-aucSensorName OBJECT-TYPE
        SYNTAX DisplayString
        ACCESS accessible-for-notify
        STATUS current
        DESCRIPTION 
            "Sensor name"
        ::= {trap-30744-addinfo 8}

-- 1.3.6.1.4.1.3902.6053.19.1.3.11.1.30744
    trapCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-alarm 30744}

-- 1.3.6.1.4.1.3902.6053.19.1.3.11.1.30744
    trap-30744-reasoninfo OBJECT IDENTIFIER ::= {trap-alarm 30744}

-- 1.3.6.1.4.1.3902.6053.19.1.3.11.1.30744.0
    trapUnspecifiedCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 0}

-- 1.3.6.1.4.1.3902.6053.19.1.3.11.1.30744.1
    trapOtherCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 1}

-- 1.3.6.1.4.1.3902.6053.19.1.3.11.1.30744.2
    trapUnkownCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 2}

-- 1.3.6.1.4.1.3902.6053.19.1.3.11.1.30744.3
    trapProcessorCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 3}

-- 1.3.6.1.4.1.3902.6053.19.1.3.11.1.30744.4
    trapDiskCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 4}

-- 1.3.6.1.4.1.3902.6053.19.1.3.11.1.30744.5
    trapPeripheralCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 5}

-- 1.3.6.1.4.1.3902.6053.19.1.3.11.1.30744.6
    trapSystemManagementModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 6}

-- 1.3.6.1.4.1.3902.6053.19.1.3.11.1.30744.7
    trapSystemBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 7}

-- 1.3.6.1.4.1.3902.6053.19.1.3.11.1.30744.8
    trapMemoryCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 8}

-- 1.3.6.1.4.1.3902.6053.19.1.3.11.1.30744.9
    trapProcessorModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 9}

-- 1.3.6.1.4.1.3902.6053.19.1.3.11.1.30744.10
    trapPowerSupplyCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 10}

-- 1.3.6.1.4.1.3902.6053.19.1.3.11.1.30744.11
    trapADDINCardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 11}

-- 1.3.6.1.4.1.3902.6053.19.1.3.11.1.30744.12
    trapFrontPanelBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 12}

-- 1.3.6.1.4.1.3902.6053.19.1.3.11.1.30744.13
    trapBackPanelBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 13}

-- 1.3.6.1.4.1.3902.6053.19.1.3.11.1.30744.14
    trapPowerSystemBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 14}

-- 1.3.6.1.4.1.3902.6053.19.1.3.11.1.30744.15
    trapDriveBackplaneCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 15}

-- 1.3.6.1.4.1.3902.6053.19.1.3.11.1.30744.16
    trapSystemInternalExpansionBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 16}

-- 1.3.6.1.4.1.3902.6053.19.1.3.11.1.30744.17
    trapOtherSystemBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 17}

-- 1.3.6.1.4.1.3902.6053.19.1.3.11.1.30744.18
    trapProcessorBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 18}

-- 1.3.6.1.4.1.3902.6053.19.1.3.11.1.30744.19
    trapPowerUnitCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 19}

-- 1.3.6.1.4.1.3902.6053.19.1.3.11.1.30744.20
    trapPowerModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 20}

-- 1.3.6.1.4.1.3902.6053.19.1.3.11.1.30744.21
    trapPowerManagementBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 21}

-- 1.3.6.1.4.1.3902.6053.19.1.3.11.1.30744.22
    trapChassisBackPanelBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 22}

-- 1.3.6.1.4.1.3902.6053.19.1.3.11.1.30744.23
    trapSystemChassisCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 23}

-- 1.3.6.1.4.1.3902.6053.19.1.3.11.1.30744.24
    trapSUBChassisCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 24}

-- 1.3.6.1.4.1.3902.6053.19.1.3.11.1.30744.25
    trapOtherChassisBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 25}

-- 1.3.6.1.4.1.3902.6053.19.1.3.11.1.30744.26
    trapDiskDriveCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 26}

-- 1.3.6.1.4.1.3902.6053.19.1.3.11.1.30744.27
    trapPeripheralBayCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 27}

-- 1.3.6.1.4.1.3902.6053.19.1.3.11.1.30744.28
    trapDeviceBayCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 28}

-- 1.3.6.1.4.1.3902.6053.19.1.3.11.1.30744.29
    trapFanCoolingCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 29}

-- 1.3.6.1.4.1.3902.6053.19.1.3.11.1.30744.30
    trapCoolingUnitCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 30}

-- 1.3.6.1.4.1.3902.6053.19.1.3.11.1.30744.31
    trapCableInterconnectCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 31}

-- 1.3.6.1.4.1.3902.6053.19.1.3.11.1.30744.32
    trapMemoryDeviceCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 32}

-- 1.3.6.1.4.1.3902.6053.19.1.3.11.1.30744.33
    trapSystemManagementSoftwareCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 33}

-- 1.3.6.1.4.1.3902.6053.19.1.3.11.1.30744.34
    trapBiosCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 34}

-- 1.3.6.1.4.1.3902.6053.19.1.3.11.1.30744.35
    trapOperatingSystemCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 35}

-- 1.3.6.1.4.1.3902.6053.19.1.3.11.1.30744.36
    trapSystemBusCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 36}

-- 1.3.6.1.4.1.3902.6053.19.1.3.11.1.30744.37
    trapGroupCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 37}

-- 1.3.6.1.4.1.3902.6053.19.1.3.11.1.30744.38
    trapRemotManagementDeviceCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 38}

-- 1.3.6.1.4.1.3902.6053.19.1.3.11.1.30744.39
    trapExternalEnvironmentCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 39}

-- 1.3.6.1.4.1.3902.6053.19.1.3.11.1.30744.40
    trapBatteryCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 40}

-- 1.3.6.1.4.1.3902.6053.19.1.3.11.1.30744.41
    trapProcessBladeModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 41}

-- 1.3.6.1.4.1.3902.6053.19.1.3.11.1.30744.42
    trapConnectivitySwitchCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 42}

-- 1.3.6.1.4.1.3902.6053.19.1.3.11.1.30744.43
    trapProcessorMemoryModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 43}

-- 1.3.6.1.4.1.3902.6053.19.1.3.11.1.30744.44
    trapIOModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 44}

-- 1.3.6.1.4.1.3902.6053.19.1.3.11.1.30744.45
    trapProcessorIOModuleCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 45}

-- 1.3.6.1.4.1.3902.6053.19.1.3.11.1.30744.46
    trapMGMTControllerFirmwareCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 46}

-- 1.3.6.1.4.1.3902.6053.19.1.3.11.1.30744.47
    trapIPMIChannelCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 47}

-- 1.3.6.1.4.1.3902.6053.19.1.3.11.1.30744.48
    trapPCIBUSCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 48}

-- 1.3.6.1.4.1.3902.6053.19.1.3.11.1.30744.49
    trapPCIExpressBUSCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 49}

-- 1.3.6.1.4.1.3902.6053.19.1.3.11.1.30744.50
    trapSCSIBUSCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 50}

-- 1.3.6.1.4.1.3902.6053.19.1.3.11.1.30744.51
    trapSATASASBUSCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 51}

-- 1.3.6.1.4.1.3902.6053.19.1.3.11.1.30744.52
    trapProcessorFrontSideBUSCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 52}

-- 1.3.6.1.4.1.3902.6053.19.1.3.11.1.30744.53
    trapRealTimeClockCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 53}

-- 1.3.6.1.4.1.3902.6053.19.1.3.11.1.30744.54
    trapSystemFirmwareCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 54}

-- 1.3.6.1.4.1.3902.6053.19.1.3.11.1.30744.160
    trapMainBoardCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 160}

-- 1.3.6.1.4.1.3902.6053.19.1.3.11.1.30744.208
    trapNetPortCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 208}

-- 1.3.6.1.4.1.3902.6053.19.1.3.11.1.30744.209
    trapLogicalDiskCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 209}

-- 1.3.6.1.4.1.3902.6053.19.1.3.11.1.30744.210
    trapStorageCTRLCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 210}

-- 1.3.6.1.4.1.3902.6053.19.1.3.11.1.30744.272
    trapNICSFPCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 272}

-- 1.3.6.1.4.1.3902.6053.19.1.3.11.1.30744.273
    trapOCPSFPCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 273}

-- 1.3.6.1.4.1.3902.6053.19.1.3.11.1.30744.275
    trapSNICSFPCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 28}

-- 1.3.6.1.4.1.3902.6053.19.1.3.11.1.30744.277
    trapDPUT100CurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 277}

-- 1.3.6.1.4.1.3902.6053.19.1.3.11.1.30744.278
    trapDPUT200CurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 278}

-- 1.3.6.1.4.1.3902.6053.19.1.3.11.1.30744.279
    trapBSC25GCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 279}

-- 1.3.6.1.4.1.3902.6053.19.1.3.11.1.30744.281
    trapNEOCurrentIsHigherThanUpperNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30744-ucFruId, trap-30744-aucCurrentValue, trap-30744-aucThresholdValue, trap-30744-aucUnitStr, trap-30744-aucSensorName, acTrapTime, acTrapEventSubject, acTrapSeverity, acTrapDescription, acTrapProductSerial, acTrapState, acTrapDeviceSN, acTrapAddInform, dwTrapIndex
		                                        }
		STATUS			current
		DESCRIPTION		"Current is higher than upper-non-recoverable threshold."
		::=  {  trap-30744-reasoninfo 281}

-- 1.3.6.1.4.1.3902.6053.19.1.3.11.1.30745
    trap-30745-addinfo OBJECT IDENTIFIER ::= {trap-addinfo 30745}

-- 1.3.6.1.4.1.3902.6053.19.1.3.11.2.30745.1
    trap-30745-ucFruId OBJECT-TYPE
        SYNTAX Unsigned32
        ACCESS accessible-for-notify
        STATUS current
        DESCRIPTION 
            "FRU ID"
        ::= {trap-30745-addinfo 1}

-- 1.3.6.1.4.1.3902.6053.19.1.3.11.2.30745.5
    trap-30745-aucCurrentValue OBJECT-TYPE
        SYNTAX DisplayString
        ACCESS accessible-for-notify
        STATUS current
        DESCRIPTION 
            "Current value"
        ::= {trap-30745-addinfo 5}

-- 1.3.6.1.4.1.3902.6053.19.1.3.11.2.30745.6
    trap-30745-aucThresholdValue OBJECT-TYPE
        SYNTAX DisplayString
        ACCESS accessible-for-notify
        STATUS current
        DESCRIPTION 
            "Threshold value"
        ::= {trap-30745-addinfo 6}

-- 1.3.6.1.4.1.3902.6053.19.1.3.11.2.30745.7
    trap-30745-aucUnitStr OBJECT-TYPE
        SYNTAX DisplayString
        ACCESS accessible-for-notify
        STATUS current
        DESCRIPTION 
            "Unit"
        ::= {trap-30745-addinfo 7}

-- 1.3.6.1.4.1.3902.6053.19.1.3.11.2.30745.8
    trap-30745-aucSensorName OBJECT-TYPE
        SYNTAX DisplayString
        ACCESS accessible-for-notify
        STATUS current
        DESCRIPTION 
            "Sensor name"
        ::= {trap-30745-addinfo 8}

-- 1.3.6.1.4.1.3902.6053.19.1.3.11.1.30745
    trapVelocityOfFanIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30745-ucFruId, trap-30745-aucCurrentValue, trap-30745-aucThresholdValue, trap-30745-aucUnitStr, trap-30745-aucSensorName, acTrapTime, acTrapEventSubject, acTrapSeverity, acTrapDescription, acTrapProductSerial, acTrapState, acTrapDeviceSN, acTrapAddInform, dwTrapIndex
		                                        }
		STATUS			current
		DESCRIPTION		"Velocity of fan is lower than lower-non-critical threshold."
		::=  {  trap-alarm 30745}

-- 1.3.6.1.4.1.3902.6053.19.1.3.11.1.30745
    trap-30745-reasoninfo OBJECT IDENTIFIER ::= {trap-alarm 30745}

-- 1.3.6.1.4.1.3902.6053.19.1.3.11.1.30745.1
    trapSpeedOfFanIsLowerThanLowerNonCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30745-ucFruId, trap-30745-aucCurrentValue, trap-30745-aucThresholdValue, trap-30745-aucUnitStr, trap-30745-aucSensorName, acTrapTime, acTrapEventSubject, acTrapSeverity, acTrapDescription, acTrapProductSerial, acTrapState, acTrapDeviceSN, acTrapAddInform, dwTrapIndex
		                                        }
		STATUS			current
		DESCRIPTION		"Velocity of fan is lower than lower-non-critical threshold."
		::=  {  trap-30745-reasoninfo 1}

-- 1.3.6.1.4.1.3902.6053.19.1.3.11.1.30746
    trap-30746-addinfo OBJECT IDENTIFIER ::= {trap-addinfo 30746}

-- 1.3.6.1.4.1.3902.6053.19.1.3.11.2.30746.1
    trap-30746-ucFruId OBJECT-TYPE
        SYNTAX Unsigned32
        ACCESS accessible-for-notify
        STATUS current
        DESCRIPTION 
            "FRU ID"
        ::= {trap-30746-addinfo 1}

-- 1.3.6.1.4.1.3902.6053.19.1.3.11.2.30746.5
    trap-30746-aucCurrentValue OBJECT-TYPE
        SYNTAX DisplayString
        ACCESS accessible-for-notify
        STATUS current
        DESCRIPTION 
            "Current value"
        ::= {trap-30746-addinfo 5}

-- 1.3.6.1.4.1.3902.6053.19.1.3.11.2.30746.6
    trap-30746-aucThresholdValue OBJECT-TYPE
        SYNTAX DisplayString
        ACCESS accessible-for-notify
        STATUS current
        DESCRIPTION 
            "Threshold value"
        ::= {trap-30746-addinfo 6}

-- 1.3.6.1.4.1.3902.6053.19.1.3.11.2.30746.7
    trap-30746-aucUnitStr OBJECT-TYPE
        SYNTAX DisplayString
        ACCESS accessible-for-notify
        STATUS current
        DESCRIPTION 
            "Unit"
        ::= {trap-30746-addinfo 7}

-- 1.3.6.1.4.1.3902.6053.19.1.3.11.2.30746.8
    trap-30746-aucSensorName OBJECT-TYPE
        SYNTAX DisplayString
        ACCESS accessible-for-notify
        STATUS current
        DESCRIPTION 
            "Sensor name"
        ::= {trap-30746-addinfo 8}

-- 1.3.6.1.4.1.3902.6053.19.1.3.11.1.30746
    trapVelocityOfFanIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30746-ucFruId, trap-30746-aucCurrentValue, trap-30746-aucThresholdValue, trap-30746-aucUnitStr, trap-30746-aucSensorName, acTrapTime, acTrapEventSubject, acTrapSeverity, acTrapDescription, acTrapProductSerial, acTrapState, acTrapDeviceSN, acTrapAddInform, dwTrapIndex
		                                        }
		STATUS			current
		DESCRIPTION		"Velocity of fan is lower than lower-non-recoverable threshold."
		::=  {  trap-alarm 30746}

-- 1.3.6.1.4.1.3902.6053.19.1.3.11.1.30746
    trap-30746-reasoninfo OBJECT IDENTIFIER ::= {trap-alarm 30746}

-- 1.3.6.1.4.1.3902.6053.19.1.3.11.1.30746.1
    trapSpeedOfFanIsLowerThanLowerNonRecoverableThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30746-ucFruId, trap-30746-aucCurrentValue, trap-30746-aucThresholdValue, trap-30746-aucUnitStr, trap-30746-aucSensorName, acTrapTime, acTrapEventSubject, acTrapSeverity, acTrapDescription, acTrapProductSerial, acTrapState, acTrapDeviceSN, acTrapAddInform, dwTrapIndex
		                                        }
		STATUS			current
		DESCRIPTION		"Velocity of fan is lower than lower-non-recoverable threshold."
		::=  {  trap-30746-reasoninfo 1}

-- 1.3.6.1.4.1.3902.6053.19.1.3.11.1.30752
    trap-30752-addinfo OBJECT IDENTIFIER ::= {trap-addinfo 30752}

-- 1.3.6.1.4.1.3902.6053.19.1.3.11.2.30752.1
    trap-30752-ucEthId OBJECT-TYPE
        SYNTAX Unsigned32
        ACCESS accessible-for-notify
        STATUS current
        DESCRIPTION 
            "Eth ID"
        ::= {trap-30752-addinfo 1}

-- 1.3.6.1.4.1.3902.6053.19.1.3.11.2.30752.3
    trap-30752-ucLocation OBJECT-TYPE
        SYNTAX Unsigned32
        ACCESS accessible-for-notify
        STATUS current
        DESCRIPTION 
            "Location"
        ::= {trap-30752-addinfo 3}

-- 1.3.6.1.4.1.3902.6053.19.1.3.11.1.30752
    trapNicPortLinkStateIsDown  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30752-ucEthId, trap-30752-ucLocation, acTrapTime, acTrapEventSubject, acTrapSeverity, acTrapDescription, acTrapProductSerial, acTrapState, acTrapDeviceSN, acTrapAddInform, dwTrapIndex
		                                        }
		STATUS			current
		DESCRIPTION		"NIC port link state is down."
		::=  {  trap-alarm 30752}

-- 1.3.6.1.4.1.3902.6053.19.1.3.11.1.30752
    trap-30752-reasoninfo OBJECT IDENTIFIER ::= {trap-alarm 30752}

-- 1.3.6.1.4.1.3902.6053.19.1.3.11.1.30752.1
    trapEmbeddedNicPortLinkStateIsDown  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30752-ucEthId, trap-30752-ucLocation, acTrapTime, acTrapEventSubject, acTrapSeverity, acTrapDescription, acTrapProductSerial, acTrapState, acTrapDeviceSN, acTrapAddInform, dwTrapIndex
		                                        }
		STATUS			current
		DESCRIPTION		"NIC port link state is down."
		::=  {  trap-30752-reasoninfo 1}

-- 1.3.6.1.4.1.3902.6053.19.1.3.11.1.30752.2
    trapOcpNicPortLinkStateIsDown  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30752-ucEthId, trap-30752-ucLocation, acTrapTime, acTrapEventSubject, acTrapSeverity, acTrapDescription, acTrapProductSerial, acTrapState, acTrapDeviceSN, acTrapAddInform, dwTrapIndex
		                                        }
		STATUS			current
		DESCRIPTION		"NIC port link state is down."
		::=  {  trap-30752-reasoninfo 2}

-- 1.3.6.1.4.1.3902.6053.19.1.3.11.1.30752.3
    trapSlotNicPortLinkStateIsDown  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30752-ucEthId, trap-30752-ucLocation, acTrapTime, acTrapEventSubject, acTrapSeverity, acTrapDescription, acTrapProductSerial, acTrapState, acTrapDeviceSN, acTrapAddInform, dwTrapIndex
		                                        }
		STATUS			current
		DESCRIPTION		"NIC port link state is down."
		::=  {  trap-30752-reasoninfo 3}

-- 1.3.6.1.4.1.3902.6053.19.1.3.11.1.30756
    trap-30756-addinfo OBJECT IDENTIFIER ::= {trap-addinfo 30756}

-- 1.3.6.1.4.1.3902.6053.19.1.3.11.2.30756.1
    trap-30756-ucAlarmReason OBJECT-TYPE
        SYNTAX Unsigned32
        ACCESS accessible-for-notify
        STATUS current
        DESCRIPTION 
            "Power major alarm reason"
        ::= {trap-30756-addinfo 1}

-- 1.3.6.1.4.1.3902.6053.19.1.3.11.1.30756
    trapPowerMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-alarm 30756}

-- 1.3.6.1.4.1.3902.6053.19.1.3.11.1.30756
    trap-30756-reasoninfo OBJECT IDENTIFIER ::= {trap-alarm 30756}

-- 1.3.6.1.4.1.3902.6053.19.1.3.11.1.30756.1
    trapPowerOvertemperatureMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 1}

-- 1.3.6.1.4.1.3902.6053.19.1.3.11.1.30756.2
    trapPowerFan2MajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 2}

-- 1.3.6.1.4.1.3902.6053.19.1.3.11.1.30756.3
    trapPowerFan1MajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 3}

-- 1.3.6.1.4.1.3902.6053.19.1.3.11.1.30756.4
    trapPowerInputUndervoltageMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 4}

-- 1.3.6.1.4.1.3902.6053.19.1.3.11.1.30756.5
    trapPowerInputOvervoltageMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 5}

-- 1.3.6.1.4.1.3902.6053.19.1.3.11.1.30756.6
    trapPowerOutputUndercurrentMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 6}

-- 1.3.6.1.4.1.3902.6053.19.1.3.11.1.30756.7
    trapPowerOutputOvercurrentMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 7}

-- 1.3.6.1.4.1.3902.6053.19.1.3.11.1.30756.8
    trapPowerOutputUndervoltageMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 8}

-- 1.3.6.1.4.1.3902.6053.19.1.3.11.1.30756.9
    trapPowerOutputOvervoltageMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 9}

-- 1.3.6.1.4.1.3902.6053.19.1.3.11.1.30756.10
    trapPowerSupplyModuleMajorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30756-ucAlarmReason, acTrapTime, acTrapEventSubject, acTrapSeverity, acTrapDescription, acTrapProductSerial, acTrapState, acTrapDeviceSN, acTrapAddInform, dwTrapIndex
		                                        }
		STATUS			current
		DESCRIPTION		"Power major fault."
		::=  {  trap-30756-reasoninfo 10}

-- 1.3.6.1.4.1.3902.6053.19.1.3.11.1.30758
    trap-30758-addinfo OBJECT IDENTIFIER ::= {trap-addinfo 30758}

-- 1.3.6.1.4.1.3902.6053.19.1.3.11.2.30758.1
    trap-30758-ucAlarmReason OBJECT-TYPE
        SYNTAX Unsigned32
        ACCESS accessible-for-notify
        STATUS current
        DESCRIPTION 
            "Power minor alarm reason"
        ::= {trap-30758-addinfo 1}

-- 1.3.6.1.4.1.3902.6053.19.1.3.11.1.30758
    trapPowerMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-alarm 30758}

-- 1.3.6.1.4.1.3902.6053.19.1.3.11.1.30758
    trap-30758-reasoninfo OBJECT IDENTIFIER ::= {trap-alarm 30758}

-- 1.3.6.1.4.1.3902.6053.19.1.3.11.1.30758.1
    trapPowerOvertemperatureMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 1}

-- 1.3.6.1.4.1.3902.6053.19.1.3.11.1.30758.2
    trapPowerFan2MinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 2}

-- 1.3.6.1.4.1.3902.6053.19.1.3.11.1.30758.3
    trapPowerFan1MinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 3}

-- 1.3.6.1.4.1.3902.6053.19.1.3.11.1.30758.4
    trapPowerInputUndervoltageMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 4}

-- 1.3.6.1.4.1.3902.6053.19.1.3.11.1.30758.5
    trapPowerInputOvervoltageMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 5}

-- 1.3.6.1.4.1.3902.6053.19.1.3.11.1.30758.6
    trapPowerOutputOvercurrentMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 6}

-- 1.3.6.1.4.1.3902.6053.19.1.3.11.1.30758.7
    trapPowerOutputUndervoltageMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 7}

-- 1.3.6.1.4.1.3902.6053.19.1.3.11.1.30758.8
    trapPowerOutputOvervoltageMinorFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30758-ucAlarmReason, acTrapTime, acTrapEventSubject, acTrapSeverity, acTrapDescription, acTrapProductSerial, acTrapState, acTrapDeviceSN, acTrapAddInform, dwTrapIndex
		                                        }
		STATUS			current
		DESCRIPTION		"Power minor fault."
		::=  {  trap-30758-reasoninfo 8}

-- 1.3.6.1.4.1.3902.6053.19.1.3.11.1.30759
    trap-30759-addinfo OBJECT IDENTIFIER ::= {trap-addinfo 30759}

-- 1.3.6.1.4.1.3902.6053.19.1.3.11.2.30759.2
    trap-30759-ucMemoryLocation OBJECT-TYPE
        SYNTAX Unsigned32
        ACCESS accessible-for-notify
        STATUS current
        DESCRIPTION 
            "Memory location"
        ::= {trap-30759-addinfo 2}

-- 1.3.6.1.4.1.3902.6053.19.1.3.11.2.30759.3
    trap-30759-ucSlotId OBJECT-TYPE
        SYNTAX Unsigned32
        {
            na(255)
        }
        ACCESS accessible-for-notify
        STATUS current
        DESCRIPTION 
            "Memory Riser Index"
        ::= {trap-30759-addinfo 3}

-- 1.3.6.1.4.1.3902.6053.19.1.3.11.1.30759
    trapFaultMemoryIsolation  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30759-ucMemoryLocation, trap-30759-ucSlotId, acTrapTime, acTrapEventSubject, acTrapSeverity, acTrapDescription, acTrapProductSerial, acTrapState, acTrapDeviceSN, acTrapAddInform, dwTrapIndex
		                                        }
		STATUS			current
		DESCRIPTION		"Fault memory isolation."
		::=  {  trap-alarm 30759}

-- 1.3.6.1.4.1.3902.6053.19.1.3.11.1.30759
    trap-30759-reasoninfo OBJECT IDENTIFIER ::= {trap-alarm 30759}

-- 1.3.6.1.4.1.3902.6053.19.1.3.11.1.30759.1
    trapFaultMemoryIsolationByBios  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30759-ucMemoryLocation, trap-30759-ucSlotId, acTrapTime, acTrapEventSubject, acTrapSeverity, acTrapDescription, acTrapProductSerial, acTrapState, acTrapDeviceSN, acTrapAddInform, dwTrapIndex
		                                        }
		STATUS			current
		DESCRIPTION		"Fault memory isolation."
		::=  {  trap-30759-reasoninfo 1}

-- 1.3.6.1.4.1.3902.6053.19.1.3.11.1.30762
    trapBoardPoweredOnFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-alarm 30762}

-- 1.3.6.1.4.1.3902.6053.19.1.3.11.1.30762
    trap-30762-reasoninfo OBJECT IDENTIFIER ::= {trap-alarm 30762}

-- 1.3.6.1.4.1.3902.6053.19.1.3.11.1.30762.1
    trapBoardPoweredOnFailureForBMCfruCheckFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 1}

-- 1.3.6.1.4.1.3902.6053.19.1.3.11.1.30762.2
    trapBoardPoweredOnFailureForFruFirmwareNotMatchBoard  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 2}

-- 1.3.6.1.4.1.3902.6053.19.1.3.11.1.30762.3
    trapBoardPoweredOnFailureForServerInS5State  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 3}

-- 1.3.6.1.4.1.3902.6053.19.1.3.11.1.30762.4
    trapBoardPoweredOnFailureForNeededRTMNotOnlinee  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 4}

-- 1.3.6.1.4.1.3902.6053.19.1.3.11.1.30762.5
    trapBoardPoweredOnFailureForBMCFatalError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 5}

-- 1.3.6.1.4.1.3902.6053.19.1.3.11.1.30762.6
    trapBoardPoweredOnFailureForMOSCheckError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 6}

-- 1.3.6.1.4.1.3902.6053.19.1.3.11.1.30762.7
    trapBoardPoweredOnFailureForVRFirmwareFrror  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 7}

-- 1.3.6.1.4.1.3902.6053.19.1.3.11.1.30762.8
    trapBoardPoweredOnFailureForInvalidPowerGoodSignal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board powered on failure"
		::=  {  trap-30762-reasoninfo 8}

-- 1.3.6.1.4.1.3902.6053.19.1.3.11.1.30763
    trap-30763-addinfo OBJECT IDENTIFIER ::= {trap-addinfo 30763}

-- 1.3.6.1.4.1.3902.6053.19.1.3.11.2.30763.1
    trap-30763-ucIntrusionLocation OBJECT-TYPE
        SYNTAX Unsigned32
        ACCESS accessible-for-notify
        STATUS current
        DESCRIPTION 
            "System intrusion Location"
        ::= {trap-30763-addinfo 1}

-- 1.3.6.1.4.1.3902.6053.19.1.3.11.1.30763
    trapSystemIntrusion  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30763-ucIntrusionLocation, acTrapTime, acTrapEventSubject, acTrapSeverity, acTrapDescription, acTrapProductSerial, acTrapState, acTrapDeviceSN, acTrapAddInform, dwTrapIndex
		                                        }
		STATUS			current
		DESCRIPTION		"System Intrusion."
		::=  {  trap-alarm 30763}

-- 1.3.6.1.4.1.3902.6053.19.1.3.11.1.30763
    trap-30763-reasoninfo OBJECT IDENTIFIER ::= {trap-alarm 30763}

-- 1.3.6.1.4.1.3902.6053.19.1.3.11.1.30763.1
    trapSystemChassisIntrusion  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30763-ucIntrusionLocation, acTrapTime, acTrapEventSubject, acTrapSeverity, acTrapDescription, acTrapProductSerial, acTrapState, acTrapDeviceSN, acTrapAddInform, dwTrapIndex
		                                        }
		STATUS			current
		DESCRIPTION		"System Intrusion."
		::=  {  trap-30763-reasoninfo 1}

-- 1.3.6.1.4.1.3902.6053.19.1.3.11.1.30765
    trap-30765-addinfo OBJECT IDENTIFIER ::= {trap-addinfo 30765}

-- 1.3.6.1.4.1.3902.6053.19.1.3.11.2.30765.1
    trap-30765-ucCpuErrType OBJECT-TYPE
        SYNTAX Unsigned32
        ACCESS accessible-for-notify
        STATUS current
        DESCRIPTION 
            "CPU error type"
        ::= {trap-30765-addinfo 1}

-- 1.3.6.1.4.1.3902.6053.19.1.3.11.1.30765
    trapCpuError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30765-ucCpuErrType, acTrapTime, acTrapEventSubject, acTrapSeverity, acTrapDescription, acTrapProductSerial, acTrapState, acTrapDeviceSN, acTrapAddInform, dwTrapIndex
		                                        }
		STATUS			current
		DESCRIPTION		"CPU error."
		::=  {  trap-alarm 30765}

-- 1.3.6.1.4.1.3902.6053.19.1.3.11.1.30765
    trap-30765-reasoninfo OBJECT IDENTIFIER ::= {trap-alarm 30765}

-- 1.3.6.1.4.1.3902.6053.19.1.3.11.1.30765.1
    trapCpuCATERRError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30765-ucCpuErrType, acTrapTime, acTrapEventSubject, acTrapSeverity, acTrapDescription, acTrapProductSerial, acTrapState, acTrapDeviceSN, acTrapAddInform, dwTrapIndex
		                                        }
		STATUS			current
		DESCRIPTION		"CPU error."
		::=  {  trap-30765-reasoninfo 1}

-- 1.3.6.1.4.1.3902.6053.19.1.3.11.1.30765.2
    trapCpuIERRError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30765-ucCpuErrType, acTrapTime, acTrapEventSubject, acTrapSeverity, acTrapDescription, acTrapProductSerial, acTrapState, acTrapDeviceSN, acTrapAddInform, dwTrapIndex
		                                        }
		STATUS			current
		DESCRIPTION		"CPU error."
		::=  {  trap-30765-reasoninfo 2}

-- 1.3.6.1.4.1.3902.6053.19.1.3.11.1.30765.3
    trapCpuUCEError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30765-ucCpuErrType, acTrapTime, acTrapEventSubject, acTrapSeverity, acTrapDescription, acTrapProductSerial, acTrapState, acTrapDeviceSN, acTrapAddInform, dwTrapIndex
		                                        }
		STATUS			current
		DESCRIPTION		"CPU error."
		::=  {  trap-30765-reasoninfo 3}

-- 1.3.6.1.4.1.3902.6053.19.1.3.11.1.30765.4
    trapCpuMCEError2  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30765-ucCpuErrType, acTrapTime, acTrapEventSubject, acTrapSeverity, acTrapDescription, acTrapProductSerial, acTrapState, acTrapDeviceSN, acTrapAddInform, dwTrapIndex
		                                        }
		STATUS			current
		DESCRIPTION		"CPU error."
		::=  {  trap-30765-reasoninfo 4}

-- 1.3.6.1.4.1.3902.6053.19.1.3.11.1.30765.5
    trapCpuUCEErrorFromBlackBox  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30765-ucCpuErrType, acTrapTime, acTrapEventSubject, acTrapSeverity, acTrapDescription, acTrapProductSerial, acTrapState, acTrapDeviceSN, acTrapAddInform, dwTrapIndex
		                                        }
		STATUS			current
		DESCRIPTION		"CPU error."
		::=  {  trap-30765-reasoninfo 5}

-- 1.3.6.1.4.1.3902.6053.19.1.3.11.1.30768
    trap-30768-addinfo OBJECT IDENTIFIER ::= {trap-addinfo 30768}

-- 1.3.6.1.4.1.3902.6053.19.1.3.11.2.30768.1
    trap-30768-ucDevType OBJECT-TYPE
        SYNTAX Unsigned32
        ACCESS accessible-for-notify
        STATUS current
        DESCRIPTION 
            "PCIE Device Type"
        ::= {trap-30768-addinfo 1}

-- 1.3.6.1.4.1.3902.6053.19.1.3.11.2.30768.2
    trap-30768-ucDevIndex OBJECT-TYPE
        SYNTAX Unsigned32
        ACCESS accessible-for-notify
        STATUS current
        DESCRIPTION 
            "Solt No"
        ::= {trap-30768-addinfo 2}

-- 1.3.6.1.4.1.3902.6053.19.1.3.11.2.30768.3
    trap-30768-ucErrorType OBJECT-TYPE
        SYNTAX Unsigned32
        ACCESS accessible-for-notify
        STATUS current
        DESCRIPTION 
            "PCIE Error Type"
        ::= {trap-30768-addinfo 3}
        
-- 1.3.6.1.4.1.3902.6053.19.1.3.11.1.30768
    trapPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-alarm 30768}

-- 1.3.6.1.4.1.3902.6053.19.1.3.11.1.30768
    trap-30768-reasoninfo OBJECT IDENTIFIER ::= {trap-alarm 30768}

-- 1.3.6.1.4.1.3902.6053.19.1.3.11.1.30768.1
    trapOnboardDiskControllerFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 1}

-- 1.3.6.1.4.1.3902.6053.19.1.3.11.1.30768.2
    trapOnboardNetcardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 2}

-- 1.3.6.1.4.1.3902.6053.19.1.3.11.1.30768.3
    trapOnboardVGAFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 3}

-- 1.3.6.1.4.1.3902.6053.19.1.3.11.1.30768.4
    trapOnboardPCIeSwitchFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 4}

-- 1.3.6.1.4.1.3902.6053.19.1.3.11.1.30768.5
    trapRTMFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 5}

-- 1.3.6.1.4.1.3902.6053.19.1.3.11.1.30768.6
    trapM2FatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 6}

-- 1.3.6.1.4.1.3902.6053.19.1.3.11.1.30768.7
    trapBackplaneFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 7}

-- 1.3.6.1.4.1.3902.6053.19.1.3.11.1.30768.8
    trapExpcardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 8}

-- 1.3.6.1.4.1.3902.6053.19.1.3.11.1.30768.9
    trapOCPCardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 9}

-- 1.3.6.1.4.1.3902.6053.19.1.3.11.1.30768.10
    trapPCIESlotFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 10}

-- 1.3.6.1.4.1.3902.6053.19.1.3.11.1.30768.11
    trapNvmeCardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 11}

-- 1.3.6.1.4.1.3902.6053.19.1.3.11.1.30768.12
    trapRaidCardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 12}

-- 1.3.6.1.4.1.3902.6053.19.1.3.11.1.30768.13
    trapNetCardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 13}

-- 1.3.6.1.4.1.3902.6053.19.1.3.11.1.30768.14
    trapSlotFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 14}

-- 1.3.6.1.4.1.3902.6053.19.1.3.11.1.30768.15
    trapSASCardFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 15}

-- 1.3.6.1.4.1.3902.6053.19.1.3.11.1.30768.16
    trapSMBUSPCIESlotFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 16}

-- 1.3.6.1.4.1.3902.6053.19.1.3.11.1.30768.17
    trapFatalPcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 17}

-- 1.3.6.1.4.1.3902.6053.19.1.3.11.1.30768.18
    trapOnboardDiskControllerUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 18}

-- 1.3.6.1.4.1.3902.6053.19.1.3.11.1.30768.19
    trapOnboardNetcardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 19}

-- 1.3.6.1.4.1.3902.6053.19.1.3.11.1.30768.20
    trapOnboardVGAUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 20}

-- 1.3.6.1.4.1.3902.6053.19.1.3.11.1.30768.21
    trapOnboardPCIeSwitchUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 21}

-- 1.3.6.1.4.1.3902.6053.19.1.3.11.1.30768.22
    trapRTMUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 22}

-- 1.3.6.1.4.1.3902.6053.19.1.3.11.1.30768.23
    trapM2UncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 23}

-- 1.3.6.1.4.1.3902.6053.19.1.3.11.1.30768.24
    trapBackplaneUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 24}

-- 1.3.6.1.4.1.3902.6053.19.1.3.11.1.30768.25
    trapExpcardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 25}

-- 1.3.6.1.4.1.3902.6053.19.1.3.11.1.30768.26
    trapOCPCardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 26}

-- 1.3.6.1.4.1.3902.6053.19.1.3.11.1.30768.27
    trapPCIESlotUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 27}

-- 1.3.6.1.4.1.3902.6053.19.1.3.11.1.30768.28
    trapNvmeCardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 28}

-- 1.3.6.1.4.1.3902.6053.19.1.3.11.1.30768.29
    trapRaidCardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 29}

-- 1.3.6.1.4.1.3902.6053.19.1.3.11.1.30768.30
    trapNetCardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 30}

-- 1.3.6.1.4.1.3902.6053.19.1.3.11.1.30768.31
    trapSlotUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 31}

-- 1.3.6.1.4.1.3902.6053.19.1.3.11.1.30768.32
    trapSASCardUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 32}

-- 1.3.6.1.4.1.3902.6053.19.1.3.11.1.30768.33
    trapSMBUSPCIESlotUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 33}

-- 1.3.6.1.4.1.3902.6053.19.1.3.11.1.30768.34
    trapUncorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30768-ucDevType, trap-30768-ucDevIndex, trap-30768-ucErrorType, acTrapTime, acTrapEventSubject, acTrapSeverity, acTrapDescription, acTrapProductSerial, acTrapState, acTrapDeviceSN, acTrapAddInform, dwTrapIndex 
		                                        }
		STATUS			current
		DESCRIPTION		"PCIE error."
		::=  {  trap-30768-reasoninfo 34}

-- 1.3.6.1.4.1.3902.6053.19.1.3.11.1.30833
    trap-30833-addinfo OBJECT IDENTIFIER ::= {trap-addinfo 30833}

-- 1.3.6.1.4.1.3902.6053.19.1.3.11.2.30833.1
    trap-30833-ucDevType OBJECT-TYPE
        SYNTAX Unsigned32
        ACCESS accessible-for-notify
        STATUS current
        DESCRIPTION 
            "PCIE Device Type"
        ::= {trap-30833-addinfo 1}

-- 1.3.6.1.4.1.3902.6053.19.1.3.11.2.30833.2
    trap-30833-ucDevIndex OBJECT-TYPE
        SYNTAX Unsigned32
        ACCESS accessible-for-notify
        STATUS current
        DESCRIPTION 
            "Solt No"
        ::= {trap-30833-addinfo 2}
      
-- 1.3.6.1.4.1.3902.6053.19.1.3.11.1.30833
    trapCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-alarm 30833}

-- 1.3.6.1.4.1.3902.6053.19.1.3.11.1.30833
    trap-30833-reasoninfo OBJECT IDENTIFIER ::= {trap-alarm 30833}

-- 1.3.6.1.4.1.3902.6053.19.1.3.11.1.30833.1
    trapOnboardDiskControllerCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 1}

-- 1.3.6.1.4.1.3902.6053.19.1.3.11.1.30833.2
    trapOnboardNetcardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 2}

-- 1.3.6.1.4.1.3902.6053.19.1.3.11.1.30833.3
    trapOnboardVGACorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 3}

-- 1.3.6.1.4.1.3902.6053.19.1.3.11.1.30833.4
    trapOnboardPCIeSwitchCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 4}

-- 1.3.6.1.4.1.3902.6053.19.1.3.11.1.30833.5
    trapRTMCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 5}

-- 1.3.6.1.4.1.3902.6053.19.1.3.11.1.30833.6
    trapM2CorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 6}

-- 1.3.6.1.4.1.3902.6053.19.1.3.11.1.30833.7
    trapBackplaneCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 7}

-- 1.3.6.1.4.1.3902.6053.19.1.3.11.1.30833.8
    trapExpcardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 8}

-- 1.3.6.1.4.1.3902.6053.19.1.3.11.1.30833.9
    trapOCPCardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 9}

-- 1.3.6.1.4.1.3902.6053.19.1.3.11.1.30833.10
    trapPCIESlotCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 10}

-- 1.3.6.1.4.1.3902.6053.19.1.3.11.1.30833.11
    trapNvmeCardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 11}

-- 1.3.6.1.4.1.3902.6053.19.1.3.11.1.30833.12
    trapRaidCardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 12}

-- 1.3.6.1.4.1.3902.6053.19.1.3.11.1.30833.13
    trapNetCardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 13}

-- 1.3.6.1.4.1.3902.6053.19.1.3.11.1.30833.14
    trapSlotCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 14}

-- 1.3.6.1.4.1.3902.6053.19.1.3.11.1.30833.15
    trapSASCardCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 15}

-- 1.3.6.1.4.1.3902.6053.19.1.3.11.1.30833.16
    trapSMBUSPCIESlotCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 16}

-- 1.3.6.1.4.1.3902.6053.19.1.3.11.1.30833.17
    trapUnKnownCorrectablePcieError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30833-ucDevType, trap-30833-ucDevIndex, acTrapTime, acTrapEventSubject, acTrapSeverity, acTrapDescription, acTrapProductSerial, acTrapState, acTrapDeviceSN, acTrapAddInform, dwTrapIndex 
		                                        }
		STATUS			current
		DESCRIPTION		"PCIE error."
		::=  {  trap-30833-reasoninfo 17}

-- 1.3.6.1.4.1.3902.6053.19.1.3.11.1.30834
    trap-30834-addinfo OBJECT IDENTIFIER ::= {trap-addinfo 30834}

-- 1.3.6.1.4.1.3902.6053.19.1.3.11.2.30834.1
    trap-30834-ucDevType OBJECT-TYPE
        SYNTAX Unsigned32
        ACCESS accessible-for-notify
        STATUS current
        DESCRIPTION 
            "PCIE Device Type"
        ::= {trap-30834-addinfo 1}

-- 1.3.6.1.4.1.3902.6053.19.1.3.11.2.30834.2
    trap-30834-ucDevIndex OBJECT-TYPE
        SYNTAX Unsigned32
        ACCESS accessible-for-notify
        STATUS current
        DESCRIPTION 
            "Solt No"
        ::= {trap-30834-addinfo 2}
        
-- 1.3.6.1.4.1.3902.6053.19.1.3.11.1.30834
    trapCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-alarm 30834} 

-- 1.3.6.1.4.1.3902.6053.19.1.3.11.1.30834
    trap-30834-reasoninfo OBJECT IDENTIFIER ::= {trap-alarm 30834}

-- 1.3.6.1.4.1.3902.6053.19.1.3.11.1.30834.1
    trapOnboardDiskControllerCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 1}

-- 1.3.6.1.4.1.3902.6053.19.1.3.11.1.30834.2
    trapOnboardNetcardCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 2}

-- 1.3.6.1.4.1.3902.6053.19.1.3.11.1.30834.3
    trapOnboardVGACorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 3}

-- 1.3.6.1.4.1.3902.6053.19.1.3.11.1.30834.4
    trapOnboardPCIeSwitchCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 4}

-- 1.3.6.1.4.1.3902.6053.19.1.3.11.1.30834.5
    trapRTMCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 5}

-- 1.3.6.1.4.1.3902.6053.19.1.3.11.1.30834.6
    trapM2CorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 6}

-- 1.3.6.1.4.1.3902.6053.19.1.3.11.1.30834.7
    trapBackplaneCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 7}

-- 1.3.6.1.4.1.3902.6053.19.1.3.11.1.30834.8
    trapExpcardCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 8}

-- 1.3.6.1.4.1.3902.6053.19.1.3.11.1.30834.9
    trapOCPCardCorrectablePcieErrorInform 	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 9}

-- 1.3.6.1.4.1.3902.6053.19.1.3.11.1.30834.10
    trapPCIESlotCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 10}

-- 1.3.6.1.4.1.3902.6053.19.1.3.11.1.30834.11
    trapNvmeCardCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 11}

-- 1.3.6.1.4.1.3902.6053.19.1.3.11.1.30834.12
    trapRaidCardCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 12}

-- 1.3.6.1.4.1.3902.6053.19.1.3.11.1.30834.13
    trapNetCardCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 13}

-- 1.3.6.1.4.1.3902.6053.19.1.3.11.1.30834.14
    trapSlotCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 14}

-- 1.3.6.1.4.1.3902.6053.19.1.3.11.1.30834.15
    trapSASCardCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 15}

-- 1.3.6.1.4.1.3902.6053.19.1.3.11.1.30834.16
    trapSMBUSPCIESlotCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 16}

-- 1.3.6.1.4.1.3902.6053.19.1.3.11.1.30834.17
    trapUnKnownCorrectablePcieErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE error inform."
		::=  {  trap-30834-reasoninfo 17}

-- 1.3.6.1.4.1.3902.6053.19.1.3.11.1.30832
    trap-30832-addinfo OBJECT IDENTIFIER ::= {trap-addinfo 30832}

-- 1.3.6.1.4.1.3902.6053.19.1.3.11.2.30832.1
    trap-30832-ucPcieSlot OBJECT-TYPE
        SYNTAX Unsigned32
        ACCESS accessible-for-notify
        STATUS current
        DESCRIPTION
            "PCIe slot"
        ::= {trap-30832-addinfo 1}

-- 1.3.6.1.4.1.3902.6053.19.1.3.11.1.30832
    trapPcieDeviceScanFailed     NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30832-ucPcieSlot, acTrapTime, acTrapEventSubject, acTrapSeverity, acTrapDescription, acTrapProductSerial, acTrapState, acTrapDeviceSN, acTrapAddInform, dwTrapIndex
                                                }
        STATUS            current
        DESCRIPTION        "PCIe device scan failed."
        ::=  {  trap-alarm 30832}        

-- 1.3.6.1.4.1.3902.6053.19.1.3.11.1.30832
    trap-30832-reasoninfo OBJECT IDENTIFIER ::= {trap-alarm 30832}

-- 1.3.6.1.4.1.3902.6053.19.1.3.11.1.30832.1
    trapPcieDeviceScanFailedAlarm     NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30832-ucPcieSlot, acTrapTime, acTrapEventSubject, acTrapSeverity, acTrapDescription, acTrapProductSerial, acTrapState, acTrapDeviceSN, acTrapAddInform, dwTrapIndex
                                                }
        STATUS            current
        DESCRIPTION        "PCIe device scan failed."
        ::=  {  trap-30832-reasoninfo 1}

-- 1.3.6.1.4.1.3902.6053.19.1.3.11.1.30772
    trap-30772-addinfo OBJECT IDENTIFIER ::= {trap-addinfo 30772}

-- 1.3.6.1.4.1.3902.6053.19.1.3.11.2.30772.2
    trap-30772-ucMemoryLocation OBJECT-TYPE
        SYNTAX Unsigned32
        ACCESS accessible-for-notify
        STATUS current
        DESCRIPTION 
            "Memory location"
        ::= {trap-30772-addinfo 2}

-- 1.3.6.1.4.1.3902.6053.19.1.3.11.2.30772.3
    trap-30772-ucSlotId OBJECT-TYPE
        SYNTAX Unsigned32
        {
            na(255)
        }
        ACCESS accessible-for-notify
        STATUS current
        DESCRIPTION 
            "Memory Riser Index"
        ::= {trap-30772-addinfo 3}

-- 1.3.6.1.4.1.3902.6053.19.1.3.11.1.30772
    trapCorrectableMemoryError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30772-ucMemoryLocation, trap-30772-ucSlotId, acTrapTime, acTrapEventSubject, acTrapSeverity, acTrapDescription, acTrapProductSerial, acTrapState, acTrapDeviceSN, acTrapAddInform, dwTrapIndex
		                                        }
		STATUS			current
		DESCRIPTION		"Correctable memory error."
		::=  {  trap-alarm 30772}

-- 1.3.6.1.4.1.3902.6053.19.1.3.11.1.30772
    trap-30772-reasoninfo OBJECT IDENTIFIER ::= {trap-alarm 30772}

-- 1.3.6.1.4.1.3902.6053.19.1.3.11.1.30772.1
    trapManyCorrectableMemoryError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30772-ucMemoryLocation, trap-30772-ucSlotId, acTrapTime, acTrapEventSubject, acTrapSeverity, acTrapDescription, acTrapProductSerial, acTrapState, acTrapDeviceSN, acTrapAddInform, dwTrapIndex
		                                        }
		STATUS			current
		DESCRIPTION		"Correctable memory error."
		::=  {  trap-30772-reasoninfo 1}

-- 1.3.6.1.4.1.3902.6053.19.1.3.11.1.30835
    trap-30835-addinfo OBJECT IDENTIFIER ::= {trap-addinfo 30835}

-- 1.3.6.1.4.1.3902.6053.19.1.3.11.2.30835.2
    trap-30835-ucMemoryLocation OBJECT-TYPE
        SYNTAX Unsigned32
        ACCESS accessible-for-notify
        STATUS current
        DESCRIPTION 
            "Memory location"
        ::= {trap-30835-addinfo 2}

-- 1.3.6.1.4.1.3902.6053.19.1.3.11.2.30835.3
    trap-30835-ucSlotId OBJECT-TYPE
        SYNTAX Unsigned32
        {
            na(255)
        }
        ACCESS accessible-for-notify
        STATUS current
        DESCRIPTION 
            "Memory Riser Index"
        ::= {trap-30835-addinfo 3}

-- 1.3.6.1.4.1.3902.6053.19.1.3.11.1.30835
    trapCorrectableMemoryErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30835-ucMemoryLocation, trap-30835-ucSlotId, acTrapTime, acTrapEventSubject, acTrapSeverity, acTrapDescription, acTrapProductSerial, acTrapState, acTrapDeviceSN, acTrapAddInform, dwTrapIndex
		                                        }
		STATUS			current
		DESCRIPTION		"Correctable memory error inform."
		::=  {  trap-alarm 30835}

-- 1.3.6.1.4.1.3902.6053.19.1.3.11.1.30835
    trap-30835-reasoninfo OBJECT IDENTIFIER ::= {trap-alarm 30835}

-- 1.3.6.1.4.1.3902.6053.19.1.3.11.1.30835.1
    trapCorrectableMemoryECCErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30835-ucMemoryLocation, trap-30835-ucSlotId, acTrapTime, acTrapEventSubject, acTrapSeverity, acTrapDescription, acTrapProductSerial, acTrapState, acTrapDeviceSN, acTrapAddInform, dwTrapIndex
		                                        }
		STATUS			current
		DESCRIPTION		"Correctable memory error inform."
		::=  {  trap-30835-reasoninfo 1}

-- 1.3.6.1.4.1.3902.6053.19.1.3.11.1.30774
    trap-30774-addinfo OBJECT IDENTIFIER ::= {trap-addinfo 30774}

-- 1.3.6.1.4.1.3902.6053.19.1.3.11.2.30774.2
    trap-30774-ucMemoryLocation OBJECT-TYPE
        SYNTAX Unsigned32
        ACCESS accessible-for-notify
        STATUS current
        DESCRIPTION 
            "Memory location"
        ::= {trap-30774-addinfo 2}

-- 1.3.6.1.4.1.3902.6053.19.1.3.11.2.30774.3
    trap-30774-ucSlotId OBJECT-TYPE
        SYNTAX Unsigned32
        {
            na(255)
        }
        ACCESS accessible-for-notify
        STATUS current
        DESCRIPTION 
            "Memory Riser Index"
        ::= {trap-30774-addinfo 3}

-- 1.3.6.1.4.1.3902.6053.19.1.3.11.1.30774
    trapCorrectableMemoryErrorLimitReachedInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30774-ucMemoryLocation, trap-30774-ucSlotId, acTrapTime, acTrapEventSubject, acTrapSeverity, acTrapDescription, acTrapProductSerial, acTrapState, acTrapDeviceSN, acTrapAddInform, dwTrapIndex
		                                        }
		STATUS			current
		DESCRIPTION		"Correctable memory error limit reached inform."
		::=  {  trap-alarm 30774}

-- 1.3.6.1.4.1.3902.6053.19.1.3.11.1.30774
    trap-30774-reasoninfo OBJECT IDENTIFIER ::= {trap-alarm 30774}

-- 1.3.6.1.4.1.3902.6053.19.1.3.11.1.30774.1
    trapCorrectableMemoryErrorLimitReachInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30774-ucMemoryLocation, trap-30774-ucSlotId, acTrapTime, acTrapEventSubject, acTrapSeverity, acTrapDescription, acTrapProductSerial, acTrapState, acTrapDeviceSN, acTrapAddInform, dwTrapIndex
		                                        }
		STATUS			current
		DESCRIPTION		"Correctable memory error limit reached inform."
		::=  {  trap-30774-reasoninfo 1}

-- 1.3.6.1.4.1.3902.6053.19.1.3.11.1.30773
    trap-30773-addinfo OBJECT IDENTIFIER ::= {trap-addinfo 30773}

-- 1.3.6.1.4.1.3902.6053.19.1.3.11.2.30773.2
    trap-30773-ucMemoryLocation OBJECT-TYPE
        SYNTAX Unsigned32
        ACCESS accessible-for-notify
        STATUS current
        DESCRIPTION 
            "Memory location"
        ::= {trap-30773-addinfo 2}

-- 1.3.6.1.4.1.3902.6053.19.1.3.11.2.30773.3
    trap-30773-ucSlotId OBJECT-TYPE
        SYNTAX Unsigned32
        {
            na(255)
        }
        ACCESS accessible-for-notify
        STATUS current
        DESCRIPTION 
            "Memory Riser Index"
        ::= {trap-30773-addinfo 3}

-- 1.3.6.1.4.1.3902.6053.19.1.3.11.1.30773
    trapUncorrectableMemoryError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30773-ucMemoryLocation, trap-30773-ucSlotId, acTrapTime, acTrapEventSubject, acTrapSeverity, acTrapDescription, acTrapProductSerial, acTrapState, acTrapDeviceSN, acTrapAddInform, dwTrapIndex
		                                        }
		STATUS			current
		DESCRIPTION		"Uncorrectable memory error."
		::=  {  trap-alarm 30773}

-- 1.3.6.1.4.1.3902.6053.19.1.3.11.1.30773
    trap-30773-reasoninfo OBJECT IDENTIFIER ::= {trap-alarm 30773}

-- 1.3.6.1.4.1.3902.6053.19.1.3.11.1.30773.1
    trapUncorrectableMemoryErrorByBios  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30773-ucMemoryLocation, trap-30773-ucSlotId, acTrapTime, acTrapEventSubject, acTrapSeverity, acTrapDescription, acTrapProductSerial, acTrapState, acTrapDeviceSN, acTrapAddInform, dwTrapIndex
		                                        }
		STATUS			current
		DESCRIPTION		"Uncorrectable memory error."
		::=  {  trap-30773-reasoninfo 1}

-- 1.3.6.1.4.1.3902.6053.19.1.3.11.1.30776
    trap-30776-addinfo OBJECT IDENTIFIER ::= {trap-addinfo 30776}

-- 1.3.6.1.4.1.3902.6053.19.1.3.11.2.30776.1
    trap-30776-dwCurrentValue OBJECT-TYPE
        SYNTAX Unsigned32
        ACCESS accessible-for-notify
        STATUS current
        DESCRIPTION 
            "Current value"
        ::= {trap-30776-addinfo 1}

-- 1.3.6.1.4.1.3902.6053.19.1.3.11.2.30776.2
    trap-30776-dwThreshold OBJECT-TYPE
        SYNTAX Unsigned32
        ACCESS accessible-for-notify
        STATUS current
        DESCRIPTION 
            "Threshold value"
        ::= {trap-30776-addinfo 2}

-- 1.3.6.1.4.1.3902.6053.19.1.3.11.2.30776.3
    trap-30776-aucUnitStr OBJECT-TYPE
        SYNTAX DisplayString
        ACCESS accessible-for-notify
        STATUS current
        DESCRIPTION 
            "Unit"
        ::= {trap-30776-addinfo 3}

-- 1.3.6.1.4.1.3902.6053.19.1.3.11.1.30776
    trapTheTotalPowerIsTooHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30776-dwCurrentValue, trap-30776-dwThreshold, trap-30776-aucUnitStr, acTrapTime, acTrapEventSubject, acTrapSeverity, acTrapDescription, acTrapProductSerial, acTrapState, acTrapDeviceSN, acTrapAddInform, dwTrapIndex
		                                        }
		STATUS			current
		DESCRIPTION		"The total power is too high."
		::=  {  trap-alarm 30776}

-- 1.3.6.1.4.1.3902.6053.19.1.3.11.1.30776
    trap-30776-reasoninfo OBJECT IDENTIFIER ::= {trap-alarm 30776}

-- 1.3.6.1.4.1.3902.6053.19.1.3.11.1.30776.1
    trapTheTotalPowerIsTooHighAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30776-dwCurrentValue, trap-30776-dwThreshold, trap-30776-aucUnitStr, acTrapTime, acTrapEventSubject, acTrapSeverity, acTrapDescription, acTrapProductSerial, acTrapState, acTrapDeviceSN, acTrapAddInform, dwTrapIndex
		                                        }
		STATUS			current
		DESCRIPTION		"The total power is too high."
		::=  {  trap-30776-reasoninfo 1} 

-- 1.3.6.1.4.1.3902.6053.19.1.3.11.1.30777
    trap-30777-addinfo OBJECT IDENTIFIER ::= {trap-addinfo 30777}

-- 1.3.6.1.4.1.3902.6053.19.1.3.11.2.30777.1
    trap-30777-aucPem1ManufactorInfo OBJECT-TYPE
        SYNTAX DisplayString
        ACCESS accessible-for-notify
        STATUS current
        DESCRIPTION 
            "Manufacture ID(PSU1)"
        ::= {trap-30777-addinfo 1}

-- 1.3.6.1.4.1.3902.6053.19.1.3.11.2.30777.2
    trap-30777-aucPem2ManufactorInfo OBJECT-TYPE
        SYNTAX DisplayString
        ACCESS accessible-for-notify
        STATUS current
        DESCRIPTION 
            "Manufacture ID(PSU2)"
        ::= {trap-30777-addinfo 2}

-- 1.3.6.1.4.1.3902.6053.19.1.3.11.2.30777.3
    trap-30777-aucPem3ManufactorInfo OBJECT-TYPE
        SYNTAX DisplayString
        ACCESS accessible-for-notify
        STATUS current
        DESCRIPTION 
            "Manufacture ID(PSU3)"
        ::= {trap-30777-addinfo 3}

-- 1.3.6.1.4.1.3902.6053.19.1.3.11.2.30777.4
    trap-30777-aucPem4ManufactorInfo OBJECT-TYPE
        SYNTAX DisplayString
        ACCESS accessible-for-notify
        STATUS current
        DESCRIPTION 
            "Manufacture ID(PSU7)"
        ::= {trap-30777-addinfo 4}

-- 1.3.6.1.4.1.3902.6053.19.1.3.11.1.30777
    trapSystemPsusAreNotCompatible  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30777-aucPem1ManufactorInfo, trap-30777-aucPem2ManufactorInfo, trap-30777-aucPem3ManufactorInfo, trap-30777-aucPem4ManufactorInfo, acTrapTime, acTrapEventSubject, acTrapSeverity, acTrapDescription, acTrapProductSerial, acTrapState, acTrapDeviceSN, acTrapAddInform, dwTrapIndex
		                                        }
		STATUS			current
		DESCRIPTION		"System psus are not compatible."
		::=  {  trap-alarm 30777}

-- 1.3.6.1.4.1.3902.6053.19.1.3.11.1.30777
    trap-30777-reasoninfo OBJECT IDENTIFIER ::= {trap-alarm 30777}

-- 1.3.6.1.4.1.3902.6053.19.1.3.11.1.30777.1
    trapSystemPsusAreNotAllSame  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30777-aucPem1ManufactorInfo, trap-30777-aucPem2ManufactorInfo, trap-30777-aucPem3ManufactorInfo, trap-30777-aucPem4ManufactorInfo, acTrapTime, acTrapEventSubject, acTrapSeverity, acTrapDescription, acTrapProductSerial, acTrapState, acTrapDeviceSN, acTrapAddInform, dwTrapIndex
		                                        }
		STATUS			current
		DESCRIPTION		"System psus are not compatible."
		::=  {  trap-30777-reasoninfo 1}

-- 1.3.6.1.4.1.3902.6053.19.1.3.11.1.30780
    trap-30780-addinfo OBJECT IDENTIFIER ::= {trap-addinfo 30780}

-- 1.3.6.1.4.1.3902.6053.19.1.3.11.2.30780.1
    trap-30780-dwErrType OBJECT-TYPE
        SYNTAX Unsigned32
        ACCESS accessible-for-notify
        STATUS current
        DESCRIPTION 
            "POST Error Type"
        ::= {trap-30780-addinfo 1}

-- 1.3.6.1.4.1.3902.6053.19.1.3.11.1.30780
    trapPostError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30780-dwErrType, acTrapTime, acTrapEventSubject, acTrapSeverity, acTrapDescription, acTrapProductSerial, acTrapState, acTrapDeviceSN, acTrapAddInform, dwTrapIndex
		                                        }
		STATUS			current
		DESCRIPTION		"POST Error."
		::=  {  trap-alarm 30780}

-- 1.3.6.1.4.1.3902.6053.19.1.3.11.1.30780
    trap-30780-reasoninfo OBJECT IDENTIFIER ::= {trap-alarm 30780}

-- 1.3.6.1.4.1.3902.6053.19.1.3.11.1.30780.1
    trapPostCPUConfigurationFailureError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30780-dwErrType, acTrapTime, acTrapEventSubject, acTrapSeverity, acTrapDescription, acTrapProductSerial, acTrapState, acTrapDeviceSN, acTrapAddInform, dwTrapIndex
		                                        }
		STATUS			current
		DESCRIPTION		"POST Error."
		::=  {  trap-30780-reasoninfo 1}

-- 1.3.6.1.4.1.3902.6053.19.1.3.11.1.30780.2
    trapPostUserAuthenticationError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30780-dwErrType, acTrapTime, acTrapEventSubject, acTrapSeverity, acTrapDescription, acTrapProductSerial, acTrapState, acTrapDeviceSN, acTrapAddInform, dwTrapIndex
		                                        }
		STATUS			current
		DESCRIPTION		"POST Error."
		::=  {  trap-30780-reasoninfo 2}

-- 1.3.6.1.4.1.3902.6053.19.1.3.11.1.30781
    trap-30781-addinfo OBJECT IDENTIFIER ::= {trap-addinfo 30781}

-- 1.3.6.1.4.1.3902.6053.19.1.3.11.2.30781.1
    trap-30781-ucCpuId OBJECT-TYPE
        SYNTAX Unsigned32
        ACCESS accessible-for-notify
        STATUS current
        DESCRIPTION 
            "CPU number"
        ::= {trap-30781-addinfo 1}

-- 1.3.6.1.4.1.3902.6053.19.1.3.11.1.30781
    trapMceFatalError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30781-ucCpuId, acTrapTime, acTrapEventSubject, acTrapSeverity, acTrapDescription, acTrapProductSerial, acTrapState, acTrapDeviceSN, acTrapAddInform, dwTrapIndex
		                                        }
		STATUS			current
		DESCRIPTION		"MCE Fatal Error."
		::=  {  trap-alarm 30781}

-- 1.3.6.1.4.1.3902.6053.19.1.3.11.1.30781
    trap-30781-reasoninfo OBJECT IDENTIFIER ::= {trap-alarm 30781}

-- 1.3.6.1.4.1.3902.6053.19.1.3.11.1.30781.1
    trapCPUMceFatalError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30781-ucCpuId, acTrapTime, acTrapEventSubject, acTrapSeverity, acTrapDescription, acTrapProductSerial, acTrapState, acTrapDeviceSN, acTrapAddInform, dwTrapIndex
		                                        }
		STATUS			current
		DESCRIPTION		"MCE Fatal Error."
		::=  {  trap-30781-reasoninfo 1}

-- 1.3.6.1.4.1.3902.6053.19.1.3.11.1.30782
    trap-30782-addinfo OBJECT IDENTIFIER ::= {trap-addinfo 30782}

-- 1.3.6.1.4.1.3902.6053.19.1.3.11.2.30782.1
    trap-30782-ucCpuId OBJECT-TYPE
        SYNTAX Unsigned32
        ACCESS accessible-for-notify
        STATUS current
        DESCRIPTION 
            "CPU number"
        ::= {trap-30782-addinfo 1}

-- 1.3.6.1.4.1.3902.6053.19.1.3.11.1.30782
    trapMceCatastrophicError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30782-ucCpuId, acTrapTime, acTrapEventSubject, acTrapSeverity, acTrapDescription, acTrapProductSerial, acTrapState, acTrapDeviceSN, acTrapAddInform, dwTrapIndex
		                                        }
		STATUS			current
		DESCRIPTION		"MCE Catastrophic Error."
		::=  {  trap-alarm 30782}

-- 1.3.6.1.4.1.3902.6053.19.1.3.11.1.30782
    trap-30782-reasoninfo OBJECT IDENTIFIER ::= {trap-alarm 30782}

-- 1.3.6.1.4.1.3902.6053.19.1.3.11.1.30782.1
    trapCPUMCECatastrophicError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30782-ucCpuId, acTrapTime, acTrapEventSubject, acTrapSeverity, acTrapDescription, acTrapProductSerial, acTrapState, acTrapDeviceSN, acTrapAddInform, dwTrapIndex
		                                        }
		STATUS			current
		DESCRIPTION		"MCE Catastrophic Error."
		::=  {  trap-30782-reasoninfo 1}

-- 1.3.6.1.4.1.3902.6053.19.1.3.11.1.30783
    trap-30783-addinfo OBJECT IDENTIFIER ::= {trap-addinfo 30783}

-- 1.3.6.1.4.1.3902.6053.19.1.3.11.2.30783.1
    trap-30783-ucCpuId OBJECT-TYPE
        SYNTAX Unsigned32
        ACCESS accessible-for-notify
        STATUS current
        DESCRIPTION 
            "CPU number"
        ::= {trap-30783-addinfo 1}

-- 1.3.6.1.4.1.3902.6053.19.1.3.11.1.30783
    trapCpuPredictiveFailureDetected  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30783-ucCpuId, acTrapTime, acTrapEventSubject, acTrapSeverity, acTrapDescription, acTrapProductSerial, acTrapState, acTrapDeviceSN, acTrapAddInform, dwTrapIndex
		                                        }
		STATUS			current
		DESCRIPTION		"CPU Predictive Failure Detected."
		::=  {  trap-alarm 30783}

-- 1.3.6.1.4.1.3902.6053.19.1.3.11.1.30783
    trap-30783-reasoninfo OBJECT IDENTIFIER ::= {trap-alarm 30783}

-- 1.3.6.1.4.1.3902.6053.19.1.3.11.1.30783.1
    trapCpuPredictiveFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30783-ucCpuId, acTrapTime, acTrapEventSubject, acTrapSeverity, acTrapDescription, acTrapProductSerial, acTrapState, acTrapDeviceSN, acTrapAddInform, dwTrapIndex
		                                        }
		STATUS			current
		DESCRIPTION		"CPU Predictive Failure Detected."
		::=  {  trap-30783-reasoninfo 1}

-- 1.3.6.1.4.1.3902.6053.19.1.3.11.1.30836
    trap-30836-addinfo OBJECT IDENTIFIER ::= {trap-addinfo 30836}

-- 1.3.6.1.4.1.3902.6053.19.1.3.11.2.30836.1
    trap-30836-ucCpuId OBJECT-TYPE
        SYNTAX Unsigned32
        ACCESS accessible-for-notify
        STATUS current
        DESCRIPTION 
            "CPU number"
        ::= {trap-30836-addinfo 1}

-- 1.3.6.1.4.1.3902.6053.19.1.3.11.1.30836
    trapCpuPredictiveFailureDetectedInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30836-ucCpuId, acTrapTime, acTrapEventSubject, acTrapSeverity, acTrapDescription, acTrapProductSerial, acTrapState, acTrapDeviceSN, acTrapAddInform, dwTrapIndex
		                                        }
		STATUS			current
		DESCRIPTION		"CPU predictive failure detected inform."
		::=  {  trap-alarm 30836}

-- 1.3.6.1.4.1.3902.6053.19.1.3.11.1.30836
    trap-30836-reasoninfo OBJECT IDENTIFIER ::= {trap-alarm 30836}

-- 1.3.6.1.4.1.3902.6053.19.1.3.11.1.30836.1
    trapCpuPredictiveFailureInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30836-ucCpuId, acTrapTime, acTrapEventSubject, acTrapSeverity, acTrapDescription, acTrapProductSerial, acTrapState, acTrapDeviceSN, acTrapAddInform, dwTrapIndex
		                                        }
		STATUS			current
		DESCRIPTION		"CPU predictive failure detected inform."
		::=  {  trap-30836-reasoninfo 1}

-- 1.3.6.1.4.1.3902.6053.19.1.3.11.1.30787
    trap-30787-addinfo OBJECT IDENTIFIER ::= {trap-addinfo 30787}

-- 1.3.6.1.4.1.3902.6053.19.1.3.11.1.30787
    trapBoardIsPoweredOn  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board is powered on."
		::=  {  trap-alarm 30787}

-- 1.3.6.1.4.1.3902.6053.19.1.3.11.1.30787
    trap-30787-reasoninfo OBJECT IDENTIFIER ::= {trap-alarm 30787}

-- 1.3.6.1.4.1.3902.6053.19.1.3.11.1.30787.1
    trapBoardIsPoweredOnStatus  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board is powered on."
		::=  {  trap-30787-reasoninfo 1}

-- 1.3.6.1.4.1.3902.6053.19.1.3.11.1.30790
    trap-30790-addinfo OBJECT IDENTIFIER ::= {trap-addinfo 30790}

-- 1.3.6.1.4.1.3902.6053.19.1.3.11.1.30790
    trapBoardIsPoweredOff  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board is powered off."
		::=  {  trap-alarm 30790}

-- 1.3.6.1.4.1.3902.6053.19.1.3.11.1.30790
    trap-30790-reasoninfo OBJECT IDENTIFIER ::= {trap-alarm 30790}

-- 1.3.6.1.4.1.3902.6053.19.1.3.11.1.30790.1
    trapBoardIsPoweredOffStatus  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Board is powered off."
		::=  {  trap-30790-reasoninfo 1}

-- 1.3.6.1.4.1.3902.6053.19.1.3.11.1.30791
    trap-30791-addinfo OBJECT IDENTIFIER ::= {trap-addinfo 30791}

-- 1.3.6.1.4.1.3902.6053.19.1.3.11.2.30791.1
    trap-30791-ucFruId OBJECT-TYPE
        SYNTAX Unsigned32
        ACCESS accessible-for-notify
        STATUS current
        DESCRIPTION 
            "Fru Id"
        ::= {trap-30791-addinfo 1}

-- 1.3.6.1.4.1.3902.6053.19.1.3.11.2.30791.3
    trap-30791-ucGeneric8Offset OBJECT-TYPE
        SYNTAX Unsigned32
        ACCESS accessible-for-notify
        STATUS current
        DESCRIPTION 
            "Generic event state (type3)"
        ::= {trap-30791-addinfo 3}

-- 1.3.6.1.4.1.3902.6053.19.1.3.11.2.30791.5
    trap-30791-aucSensorName OBJECT-TYPE
        SYNTAX DisplayString
        ACCESS accessible-for-notify
        STATUS current
        DESCRIPTION 
            "Sensor name"
        ::= {trap-30791-addinfo 5}

-- 1.3.6.1.4.1.3902.6053.19.1.3.11.1.30791
    trapPSUStatusChanged  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30791-ucFruId, trap-30791-ucGeneric8Offset, trap-30791-aucSensorName, acTrapTime, acTrapEventSubject, acTrapSeverity, acTrapDescription, acTrapProductSerial, acTrapState, acTrapDeviceSN, acTrapAddInform, dwTrapIndex
		                                        }
		STATUS			current
		DESCRIPTION		"PSU Status is Changed"
		::=  {  trap-alarm 30791}

-- 1.3.6.1.4.1.3902.6053.19.1.3.11.1.30791
    trap-30791-reasoninfo OBJECT IDENTIFIER ::= {trap-alarm 30791}

-- 1.3.6.1.4.1.3902.6053.19.1.3.11.1.30791.1
    trapPSUStatusChangedInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30791-ucFruId, trap-30791-ucGeneric8Offset, trap-30791-aucSensorName, acTrapTime, acTrapEventSubject, acTrapSeverity, acTrapDescription, acTrapProductSerial, acTrapState, acTrapDeviceSN, acTrapAddInform, dwTrapIndex
		                                        }
		STATUS			current
		DESCRIPTION		"PSU Status is Changed"
		::=  {  trap-30791-reasoninfo 1}
    
-- 1.3.6.1.4.1.3902.6053.19.1.3.11.1.30810
    trap-30810-addinfo OBJECT IDENTIFIER ::= {trap-addinfo 30810}

-- 1.3.6.1.4.1.3902.6053.19.1.3.11.2.30810.1
    trap-30810-ucDiskstatus OBJECT-TYPE
        SYNTAX Unsigned32
        ACCESS accessible-for-notify
        STATUS current
        DESCRIPTION 
            "Disk status"
        ::= {trap-30810-addinfo 1}

-- 1.3.6.1.4.1.3902.6053.19.1.3.11.2.30810.2
    trap-30810-ucIdeLocation OBJECT-TYPE
        SYNTAX Unsigned32
        ACCESS accessible-for-notify
        STATUS current
        DESCRIPTION 
            "Disk location"
        ::= {trap-30810-addinfo 2}
-- 1.3.6.1.4.1.3902.6053.19.1.3.11.2.30810.3
    trap-30810-ucZone OBJECT-TYPE
        SYNTAX Unsigned32
        ACCESS accessible-for-notify
        STATUS current
        DESCRIPTION 
            "Disk zone"
        ::= {trap-30810-addinfo 3}

-- 1.3.6.1.4.1.3902.6053.19.1.3.11.1.30810
    trapHardDiskStatusChange  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30810-ucDiskstatus, trap-30810-ucIdeLocation,trap-30810-ucZone, acTrapTime, acTrapEventSubject, acTrapSeverity, acTrapDescription, acTrapProductSerial, acTrapState, acTrapDeviceSN, acTrapAddInform, dwTrapIndex
		                                        }
		STATUS			current
		DESCRIPTION		"Hard disk status change."
		::=  {  trap-alarm 30810}

-- 1.3.6.1.4.1.3902.6053.19.1.3.11.1.30810
    trap-30810-reasoninfo OBJECT IDENTIFIER ::= {trap-alarm 30810}

-- 1.3.6.1.4.1.3902.6053.19.1.3.11.1.30810.1
    trapHardDiskStatusChangeInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30810-ucDiskstatus, trap-30810-ucIdeLocation,trap-30810-ucZone, acTrapTime, acTrapEventSubject, acTrapSeverity, acTrapDescription, acTrapProductSerial, acTrapState, acTrapDeviceSN, acTrapAddInform, dwTrapIndex
		                                        }
		STATUS			current
		DESCRIPTION		"Hard disk status change."
		::=  {  trap-30810-reasoninfo 1}

-- 1.3.6.1.4.1.3902.6053.19.1.3.11.1.30815
    trap-30815-addinfo OBJECT IDENTIFIER ::= {trap-addinfo 30815}

-- 1.3.6.1.4.1.3902.6053.19.1.3.11.1.30815
    trapHostCpuResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-alarm 30815}

-- 1.3.6.1.4.1.3902.6053.19.1.3.11.1.30815
    trap-30815-reasoninfo OBJECT IDENTIFIER ::= {trap-alarm 30815}

-- 1.3.6.1.4.1.3902.6053.19.1.3.11.1.30815.1
    trapHostCpuBiosStageWDResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 1}

-- 1.3.6.1.4.1.3902.6053.19.1.3.11.1.30815.2
    trapHostCpuAppStageWDResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 2}

-- 1.3.6.1.4.1.3902.6053.19.1.3.11.1.30815.3
    trapHostCpuBiosSwitchResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 3}

-- 1.3.6.1.4.1.3902.6053.19.1.3.11.1.30815.4
    trapHostCpuOsLoadStageWDResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 4}

-- 1.3.6.1.4.1.3902.6053.19.1.3.11.1.30815.5
    trapHostCpuOsControlResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 5}

-- 1.3.6.1.4.1.3902.6053.19.1.3.11.1.30815.6
    trapHostCpuCaterrResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 6}

-- 1.3.6.1.4.1.3902.6053.19.1.3.11.1.30815.7
    trapHostCpuErrorResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 7}

-- 1.3.6.1.4.1.3902.6053.19.1.3.11.1.30815.8
    trapHostCpuBiosBootErrorResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 8}

-- 1.3.6.1.4.1.3902.6053.19.1.3.11.1.30815.9
    trapHostCpuUserControlResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 9}

-- 1.3.6.1.4.1.3902.6053.19.1.3.11.1.30815.10
    trapHostCpuUnknownResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 10}

-- 1.3.6.1.4.1.3902.6053.19.1.3.11.1.30815.11
    trapHostCpuNoReasonResetEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Host cpu reset event."
		::=  {  trap-30815-reasoninfo 11}

-- 1.3.6.1.4.1.3902.6053.19.1.3.11.1.5632
    trap-5632-addinfo OBJECT IDENTIFIER ::= {trap-addinfo 5632}

-- 1.3.6.1.4.1.3902.6053.19.1.3.11.2.5632.1
    trap-5632-acIdeName OBJECT-TYPE
        SYNTAX DisplayString
        ACCESS accessible-for-notify
        STATUS current
        DESCRIPTION 
            "Mount directory"
        ::= {trap-5632-addinfo 1}

-- 1.3.6.1.4.1.3902.6053.19.1.3.11.2.5632.2
    trap-5632-ucLevel OBJECT-TYPE
        SYNTAX Unsigned32
        ACCESS accessible-for-notify
        STATUS current
        DESCRIPTION 
            "Hard disk full alarm level"
        ::= {trap-5632-addinfo 2}

-- 1.3.6.1.4.1.3902.6053.19.1.3.11.2.5632.3
    trap-5632-ucIdeRate OBJECT-TYPE
        SYNTAX Unsigned32
        ACCESS accessible-for-notify
        STATUS current
        DESCRIPTION 
            "Hard disk used-rate"
        ::= {trap-5632-addinfo 3}

-- 1.3.6.1.4.1.3902.6053.19.1.3.11.2.5632.4
    trap-5632-ucIdeThreshold1 OBJECT-TYPE
        SYNTAX Unsigned32
        ACCESS accessible-for-notify
        STATUS current
        DESCRIPTION 
            "Hard disk usage threshold level one"
        ::= {trap-5632-addinfo 4}

-- 1.3.6.1.4.1.3902.6053.19.1.3.11.2.5632.5
    trap-5632-ucIdeThreshold2 OBJECT-TYPE
        SYNTAX Unsigned32
        ACCESS accessible-for-notify
        STATUS current
        DESCRIPTION 
            "Hard disk usage threshold level two"
        ::= {trap-5632-addinfo 5}

-- 1.3.6.1.4.1.3902.6053.19.1.3.11.2.5632.6
    trap-5632-ucIdeThreshold3 OBJECT-TYPE
        SYNTAX Unsigned32
        ACCESS accessible-for-notify
        STATUS current
        DESCRIPTION 
            "Hard disk usage threshold level three"
        ::= {trap-5632-addinfo 6}

-- 1.3.6.1.4.1.3902.6053.19.1.3.11.1.5632
    trapTheHardDiskUsedRateIsOverThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5632-acIdeName, trap-5632-ucLevel, trap-5632-ucIdeRate, trap-5632-ucIdeThreshold1, trap-5632-ucIdeThreshold2, trap-5632-ucIdeThreshold3, acTrapTime, acTrapEventSubject, acTrapSeverity, acTrapDescription, acTrapProductSerial, acTrapState, acTrapDeviceSN, acTrapAddInform, dwTrapIndex
		                                        }
		STATUS			current
		DESCRIPTION		"The hard disk used-rate is over threshold."
		::=  {  trap-alarm 5632}

-- 1.3.6.1.4.1.3902.6053.19.1.3.11.1.5632
    trap-5632-reasoninfo OBJECT IDENTIFIER ::= {trap-alarm 5632}

-- 1.3.6.1.4.1.3902.6053.19.1.3.11.1.5632.1
    trapTheHardDiskUsedRateIsOverMinorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5632-acIdeName, trap-5632-ucLevel, trap-5632-ucIdeRate, trap-5632-ucIdeThreshold1, trap-5632-ucIdeThreshold2, trap-5632-ucIdeThreshold3, acTrapTime, acTrapEventSubject, acTrapSeverity, acTrapDescription, acTrapProductSerial, acTrapState, acTrapDeviceSN, acTrapAddInform, dwTrapIndex
		                                        }
		STATUS			current
		DESCRIPTION		"The hard disk used-rate is over threshold."
		::=  {  trap-5632-reasoninfo 1}

-- 1.3.6.1.4.1.3902.6053.19.1.3.11.1.5632.2
    trapTheHardDiskUsedRateIsOverMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5632-acIdeName, trap-5632-ucLevel, trap-5632-ucIdeRate, trap-5632-ucIdeThreshold1, trap-5632-ucIdeThreshold2, trap-5632-ucIdeThreshold3, acTrapTime, acTrapEventSubject, acTrapSeverity, acTrapDescription, acTrapProductSerial, acTrapState, acTrapDeviceSN, acTrapAddInform, dwTrapIndex
		                                        }
		STATUS			current
		DESCRIPTION		"The hard disk used-rate is over threshold."
		::=  {  trap-5632-reasoninfo 2}

-- 1.3.6.1.4.1.3902.6053.19.1.3.11.1.5632.3
    trapTheHardDiskUsedRateIsOverCriticalThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5632-acIdeName, trap-5632-ucLevel, trap-5632-ucIdeRate, trap-5632-ucIdeThreshold1, trap-5632-ucIdeThreshold2, trap-5632-ucIdeThreshold3, acTrapTime, acTrapEventSubject, acTrapSeverity, acTrapDescription, acTrapProductSerial, acTrapState, acTrapDeviceSN, acTrapAddInform, dwTrapIndex
		                                        }
		STATUS			current
		DESCRIPTION		"The hard disk used-rate is over threshold."
		::=  {  trap-5632-reasoninfo 3}

-- 1.3.6.1.4.1.3902.6053.19.1.3.11.1.5797
    trap-5797-addinfo OBJECT IDENTIFIER ::= {trap-addinfo 5797}

-- 1.3.6.1.4.1.3902.6053.19.1.3.11.2.5797.1
    trap-5797-ucIdeLocation OBJECT-TYPE
        SYNTAX Unsigned32
        ACCESS accessible-for-notify
        STATUS current
        DESCRIPTION 
            "Hard disk location"
        ::= {trap-5797-addinfo 1}

-- 1.3.6.1.4.1.3902.6053.19.1.3.11.2.5797.2
    trap-5797-ucIdeErrReason OBJECT-TYPE
        SYNTAX Unsigned32
        ACCESS accessible-for-notify
        STATUS current
        DESCRIPTION 
            "Hard disk abnormal reason"
        ::= {trap-5797-addinfo 2}

-- 1.3.6.1.4.1.3902.6053.19.1.3.11.2.5797.3
    trap-5797-ucZone OBJECT-TYPE
        SYNTAX Unsigned32
        ACCESS accessible-for-notify
        STATUS current
        DESCRIPTION 
            "Disk zone"
        ::= {trap-5797-addinfo 3}

-- 1.3.6.1.4.1.3902.6053.19.1.3.11.1.5797
    trapTheHardDiskIsAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-alarm 5797}

-- 1.3.6.1.4.1.3902.6053.19.1.3.11.1.5797
    trap-5797-reasoninfo OBJECT IDENTIFIER ::= {trap-alarm 5797}

-- 1.3.6.1.4.1.3902.6053.19.1.3.11.1.5797.1
    trapTheHardDiskIsAbnormalUnknow  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 1}

-- 1.3.6.1.4.1.3902.6053.19.1.3.11.1.5797.2
    trapTheHardDiskDoesNotExist  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 2}

-- 1.3.6.1.4.1.3902.6053.19.1.3.11.1.5797.3
    trapTheHardDiskSmartIsAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 3}

-- 1.3.6.1.4.1.3902.6053.19.1.3.11.1.5797.4
    trapTheHardDiskCanNotGetSmart  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 4}

-- 1.3.6.1.4.1.3902.6053.19.1.3.11.1.5797.5
    trapTheHardDiskSmartIndexIsOverrun  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 5}

-- 1.3.6.1.4.1.3902.6053.19.1.3.11.1.5797.6
    trapTheHardDiskLiftNeedWatchful  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 6}

-- 1.3.6.1.4.1.3902.6053.19.1.3.11.1.5797.7
    trapTheHardDiskTemperatureIsHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 7}

-- 1.3.6.1.4.1.3902.6053.19.1.3.11.1.5797.8
    trapTheHardDiskLiftAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 8}

-- 1.3.6.1.4.1.3902.6053.19.1.3.11.1.5797.9
    trapTheHardDiskIsAbnormalStatus  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5797-ucIdeLocation, trap-5797-ucIdeErrReason,trap-5797-ucZone, acTrapTime, acTrapEventSubject, acTrapSeverity, acTrapDescription, acTrapProductSerial, acTrapState, acTrapDeviceSN, acTrapAddInform, dwTrapIndex
		                                        }
		STATUS			current
		DESCRIPTION		"The hard disk is abnormal."
		::=  {  trap-5797-reasoninfo 9}

-- 1.3.6.1.4.1.3902.6053.19.1.3.11.1.5800
    trap-5800-addinfo OBJECT IDENTIFIER ::= {trap-addinfo 5800}

-- 1.3.6.1.4.1.3902.6053.19.1.3.11.2.5800.1
    trap-5800-ucIdeLocation OBJECT-TYPE
        SYNTAX Unsigned32
        ACCESS accessible-for-notify
        STATUS current
        DESCRIPTION 
            "Disk location"
        ::= {trap-5800-addinfo 1}
		
-- 1.3.6.1.4.1.3902.6053.19.1.3.11.2.5800.2
    trap-5800-ucZone OBJECT-TYPE
        SYNTAX Unsigned32
        ACCESS accessible-for-notify
        STATUS current
        DESCRIPTION 
            "Disk zone"
        ::= {trap-5800-addinfo 2}

-- 1.3.6.1.4.1.3902.6053.19.1.3.11.1.5800
    trapHardDiskOffline  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5800-ucIdeLocation,trap-5800-ucZone, acTrapTime, acTrapEventSubject, acTrapSeverity, acTrapDescription, acTrapProductSerial, acTrapState, acTrapDeviceSN, acTrapAddInform, dwTrapIndex
		                                        }
		STATUS			current
		DESCRIPTION		"Hard disk offline"
		::=  {  trap-alarm 5800}

-- 1.3.6.1.4.1.3902.6053.19.1.3.11.1.5800
    trap-5800-reasoninfo OBJECT IDENTIFIER ::= {trap-addinfo 5800}

-- 1.3.6.1.4.1.3902.6053.19.1.3.11.1.5800.1
    trapHardDiskOfflineAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5800-ucIdeLocation,trap-5800-ucZone, acTrapTime, acTrapEventSubject, acTrapSeverity, acTrapDescription, acTrapProductSerial, acTrapState, acTrapDeviceSN, acTrapAddInform, dwTrapIndex
		                                        }
		STATUS			current
		DESCRIPTION		"Hard disk offline"
		::=  {  trap-5800-reasoninfo 1}

-- 1.3.6.1.4.1.3902.6053.19.1.3.11.1.5801
    trap-5801-addinfo OBJECT IDENTIFIER ::= {trap-addinfo 5801}

-- 1.3.6.1.4.1.3902.6053.19.1.3.11.2.5801.1
    trap-5801-ucCtrlSlot OBJECT-TYPE
        SYNTAX Unsigned32
        ACCESS accessible-for-notify
        STATUS current
        DESCRIPTION 
            "Controller slot"
        ::= {trap-5801-addinfo 1}

-- 1.3.6.1.4.1.3902.6053.19.1.3.11.2.5801.2
    trap-5801-ucLDIndex OBJECT-TYPE
        SYNTAX Unsigned32
        ACCESS accessible-for-notify
        STATUS current
        DESCRIPTION 
            "Virtual disk index"
        ::= {trap-5801-addinfo 2}

-- 1.3.6.1.4.1.3902.6053.19.1.3.11.2.5801.3
    trap-5801-ucRaidErrReason OBJECT-TYPE
        SYNTAX Unsigned32
        ACCESS accessible-for-notify
        STATUS current
        DESCRIPTION 
            "RAID abnormal reason"
        ::= {trap-5801-addinfo 3}

-- 1.3.6.1.4.1.3902.6053.19.1.3.11.1.5801
    trapVirtualDiskIsAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-alarm 5801}

-- 1.3.6.1.4.1.3902.6053.19.1.3.11.1.5801
    trap-5801-reasoninfo OBJECT IDENTIFIER ::= {trap-alarm 5801}

-- 1.3.6.1.4.1.3902.6053.19.1.3.11.1.5801.0
    trapVirtualDiskHD1IsUnknownAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 0}

-- 1.3.6.1.4.1.3902.6053.19.1.3.11.1.5801.1
    trapVirtualDiskHD1IsAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 1}

-- 1.3.6.1.4.1.3902.6053.19.1.3.11.1.5801.2
    trapVirtualDiskHD2IsAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 2}

-- 1.3.6.1.4.1.3902.6053.19.1.3.11.1.5801.3
    trapVirtualDiskHD1andHD2IsAbnormal 	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 3}

-- 1.3.6.1.4.1.3902.6053.19.1.3.11.1.5801.4
    trapVirtualDiskIsNotInRAIDModeAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 4}

-- 1.3.6.1.4.1.3902.6053.19.1.3.11.1.5801.5
    trapVirtualDiskIsAbnormal5  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 5}

-- 1.3.6.1.4.1.3902.6053.19.1.3.11.1.5801.6
    trapVirtualDiskIsAbnormal6  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 6}

-- 1.3.6.1.4.1.3902.6053.19.1.3.11.1.5801.7
    trapVirtualDiskIsDegradedButNotSyncAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 7}

-- 1.3.6.1.4.1.3902.6053.19.1.3.11.1.5801.8
    trapVirtualDiskIsFailedAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 8}

-- 1.3.6.1.4.1.3902.6053.19.1.3.11.1.5801.9
    trapVirtualDiskIsMissingAbnormal 	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 9}

-- 1.3.6.1.4.1.3902.6053.19.1.3.11.1.5801.10
    trapVirtualDiskIsInactiveAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 10}

-- 1.3.6.1.4.1.3902.6053.19.1.3.11.1.5801.11
    trapVirtualDiskIsOfflineAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 11}

-- 1.3.6.1.4.1.3902.6053.19.1.3.11.1.5801.12
    trapVirtualDiskIsDeletedAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5801-ucCtrlSlot, trap-5801-ucLDIndex, trap-5801-ucRaidErrReason, acTrapTime, acTrapEventSubject, acTrapSeverity, acTrapDescription, acTrapProductSerial, acTrapState, acTrapDeviceSN, acTrapAddInform, dwTrapIndex
		                                        }
		STATUS			current
		DESCRIPTION		"Virtual disk is abnormal."
		::=  {  trap-5801-reasoninfo 12}

-- 1.3.6.1.4.1.3902.6053.19.1.3.11.1.5802
    trap-5802-addinfo OBJECT IDENTIFIER ::= {trap-addinfo 5802}

-- 1.3.6.1.4.1.3902.6053.19.1.3.11.2.5802.1
    trap-5802-ucCtrlSlot OBJECT-TYPE
        SYNTAX Unsigned32
        ACCESS accessible-for-notify
        STATUS current
        DESCRIPTION 
            "Controller slot"
        ::= {trap-5802-addinfo 1}

-- 1.3.6.1.4.1.3902.6053.19.1.3.11.2.5802.2
    trap-5802-ucCtrlFaultReason OBJECT-TYPE
        SYNTAX Unsigned32
        ACCESS accessible-for-notify
        STATUS current
        DESCRIPTION 
            "RAID card abnormal reason"
        ::= {trap-5802-addinfo 2}

-- 1.3.6.1.4.1.3902.6053.19.1.3.11.1.5802
    trapRaidCardIsAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-alarm 5802}

-- 1.3.6.1.4.1.3902.6053.19.1.3.11.1.5802
    trap-5802-reasoninfo OBJECT IDENTIFIER ::= {trap-alarm 5802}

-- 1.3.6.1.4.1.3902.6053.19.1.3.11.1.5802.0
    trapEmbeddedRaidCardIsUnknownAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 0}

-- 1.3.6.1.4.1.3902.6053.19.1.3.11.1.5802.1
    trapEmbeddedRaidCardIsBBUTemperatureHighAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 1}

-- 1.3.6.1.4.1.3902.6053.19.1.3.11.1.5802.2
    trapEmbeddedRaidCardIsBBUVoltageLowAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 2}

-- 1.3.6.1.4.1.3902.6053.19.1.3.11.1.5802.3
    trapEmbeddedRaidCardIsConfigurationClearedAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 3}

-- 1.3.6.1.4.1.3902.6053.19.1.3.11.1.5802.4
    trapEmbeddedRaidCardTemperatureIsHigherThanThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 4}

-- 1.3.6.1.4.1.3902.6053.19.1.3.11.1.5802.5
    trapPCIERaidCardIsUnknownAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 5}

-- 1.3.6.1.4.1.3902.6053.19.1.3.11.1.5802.6
    trapPCIERaidCardIsBBUTemperatureHighAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 6}

-- 1.3.6.1.4.1.3902.6053.19.1.3.11.1.5802.7
    trapPCIERaidCardIsBBUVoltageLowAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 7}

-- 1.3.6.1.4.1.3902.6053.19.1.3.11.1.5802.8
    trapPCIERaidCardIsConfigurationClearedAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 8}

-- 1.3.6.1.4.1.3902.6053.19.1.3.11.1.5802.9
    trapPCIERaidCardTemperatureIsHigherThanThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-5802-ucCtrlSlot, trap-5802-ucCtrlFaultReason, acTrapTime, acTrapEventSubject, acTrapSeverity, acTrapDescription, acTrapProductSerial, acTrapState, acTrapDeviceSN, acTrapAddInform, dwTrapIndex
		                                        }
		STATUS			current
		DESCRIPTION		"RAID card is abnormal."
		::=  {  trap-5802-reasoninfo 9}

-- 1.3.6.1.4.1.3902.6053.19.1.3.11.1.30785
    trap-30785-addinfo OBJECT IDENTIFIER ::= {trap-addinfo 30785}

-- 1.3.6.1.4.1.3902.6053.19.1.3.11.2.30785.1
    trap-30785-dwCurrentValue OBJECT-TYPE
        SYNTAX Unsigned32
        ACCESS accessible-for-notify
        STATUS current
        DESCRIPTION 
            "Current value"
        ::= {trap-30785-addinfo 1}

-- 1.3.6.1.4.1.3902.6053.19.1.3.11.2.30785.2
    trap-30785-dwThresholdValue OBJECT-TYPE
        SYNTAX Unsigned32
        ACCESS accessible-for-notify
        STATUS current
        DESCRIPTION 
            "Threshold value"
        ::= {trap-30785-addinfo 2}

-- 1.3.6.1.4.1.3902.6053.19.1.3.11.2.30785.3
    trap-30785-aucUnitStr OBJECT-TYPE
        SYNTAX DisplayString
        ACCESS accessible-for-notify
        STATUS current
        DESCRIPTION 
            "Unit"
        ::= {trap-30785-addinfo 3}

-- 1.3.6.1.4.1.3902.6053.19.1.3.11.1.30785
    trapSASControllerTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30785-dwCurrentValue, trap-30785-dwThresholdValue, trap-30785-aucUnitStr, acTrapTime, acTrapEventSubject, acTrapSeverity, acTrapDescription, acTrapProductSerial, acTrapState, acTrapDeviceSN, acTrapAddInform, dwTrapIndex
		                                        }
		STATUS			current
		DESCRIPTION		"SAS controller temperature is higher than major threshold."
		::=  {  trap-alarm 30785}
		
		
-- 1.3.6.1.4.1.3902.6053.19.1.3.11.1.30786
    trap-30786-addinfo OBJECT IDENTIFIER ::= {trap-addinfo 30786}

-- 1.3.6.1.4.1.3902.6053.19.1.3.11.2.30786.1
    trap-30786-dwCurrentValue OBJECT-TYPE
        SYNTAX Unsigned32
        ACCESS accessible-for-notify
        STATUS current
        DESCRIPTION 
            "Current value"
        ::= {trap-30786-addinfo 1}

-- 1.3.6.1.4.1.3902.6053.19.1.3.11.2.30786.2
    trap-30786-dwThresholdValue OBJECT-TYPE
        SYNTAX Unsigned32
        ACCESS accessible-for-notify
        STATUS current
        DESCRIPTION 
            "Threshold value"
        ::= {trap-30786-addinfo 2}

-- 1.3.6.1.4.1.3902.6053.19.1.3.11.2.30786.3
    trap-30786-aucUnitStr OBJECT-TYPE
        SYNTAX DisplayString
        ACCESS accessible-for-notify
        STATUS current
        DESCRIPTION 
            "Unit"
        ::= {trap-30786-addinfo 3}

-- 1.3.6.1.4.1.3902.6053.19.1.3.11.1.30786
    trapDeviceTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30786-dwCurrentValue, trap-30786-dwThresholdValue, trap-30786-aucUnitStr, acTrapTime, acTrapEventSubject, acTrapSeverity, acTrapDescription, acTrapProductSerial, acTrapState, acTrapDeviceSN, acTrapAddInform, dwTrapIndex
		                                        }
		STATUS			current
		DESCRIPTION		"Device temperature is higher than major threshold."
		::=  {  trap-alarm 30786}		

-- 1.3.6.1.4.1.3902.6053.19.1.3.11.1.30786
    trap-30786-reasoninfo OBJECT IDENTIFIER ::= {trap-alarm 30786}

-- 1.3.6.1.4.1.3902.6053.19.1.3.11.1.30786.1
    trapAIAdapterTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30786-dwCurrentValue, trap-30786-dwThresholdValue, trap-30786-aucUnitStr, acTrapTime, acTrapEventSubject, acTrapSeverity, acTrapDescription, acTrapProductSerial, acTrapState, acTrapDeviceSN, acTrapAddInform, dwTrapIndex
		                                        }
		STATUS			current
		DESCRIPTION		"Device temperature is higher than major threshold."
		::=  {  trap-30786-reasoninfo 1}

-- 1.3.6.1.4.1.3902.6053.19.1.3.11.1.30786.2
    trapGpuTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30786-dwCurrentValue, trap-30786-dwThresholdValue, trap-30786-aucUnitStr, acTrapTime, acTrapEventSubject, acTrapSeverity, acTrapDescription, acTrapProductSerial, acTrapState, acTrapDeviceSN, acTrapAddInform, dwTrapIndex
		                                        }
		STATUS			current
		DESCRIPTION		"Device temperature is higher than major threshold."
		::=  {  trap-30786-reasoninfo 2}

-- 1.3.6.1.4.1.3902.6053.19.1.3.11.1.30786.3
    trapSmbusNicCardTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30786-dwCurrentValue, trap-30786-dwThresholdValue, trap-30786-aucUnitStr, acTrapTime, acTrapEventSubject, acTrapSeverity, acTrapDescription, acTrapProductSerial, acTrapState, acTrapDeviceSN, acTrapAddInform, dwTrapIndex
		                                        }
		STATUS			current
		DESCRIPTION		"Device temperature is higher than major threshold."
		::=  {  trap-30786-reasoninfo 3}  
		
-- 1.3.6.1.4.1.3902.6053.19.1.3.11.1.30786.4
    trapNcsiNicCardTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30786-dwCurrentValue, trap-30786-dwThresholdValue, trap-30786-aucUnitStr, acTrapTime, acTrapEventSubject, acTrapSeverity, acTrapDescription, acTrapProductSerial, acTrapState, acTrapDeviceSN, acTrapAddInform, dwTrapIndex
		                                        }
		STATUS			current
		DESCRIPTION		"Device temperature is higher than major threshold."
		::=  {  trap-30786-reasoninfo 4} 
		
-- 1.3.6.1.4.1.3902.6053.19.1.3.11.1.30786.5
    trapOcpNicCardTemperatureIsHigherThanMajorThreshold  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30786-dwCurrentValue, trap-30786-dwThresholdValue, trap-30786-aucUnitStr, acTrapTime, acTrapEventSubject, acTrapSeverity, acTrapDescription, acTrapProductSerial, acTrapState, acTrapDeviceSN, acTrapAddInform, dwTrapIndex
		                                        }
		STATUS			current
		DESCRIPTION		"Device temperature is higher than major threshold."
		::=  {  trap-30786-reasoninfo 5}

-- 1.3.6.1.4.1.3902.6053.19.1.3.11.1.30837
    trap-30837-addinfo OBJECT IDENTIFIER ::= {trap-addinfo 30837}

-- 1.3.6.1.4.1.3902.6053.19.1.3.11.2.30837.1
    trap-30837-serialNumber OBJECT-TYPE
        SYNTAX DisplayString
        ACCESS accessible-for-notify
        STATUS current
        DESCRIPTION 
            "server serial number"
        ::= {trap-30837-addinfo 1}

-- 1.3.6.1.4.1.3902.6053.19.1.3.11.1.30837
    trapServicesAreRecommendedToBeMovedOut  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30837-serialNumber, acTrapTime, acTrapEventSubject, acTrapSeverity, acTrapDescription, acTrapProductSerial, acTrapState, acTrapDeviceSN, acTrapAddInform, dwTrapIndex
		                                        }
		STATUS			current
		DESCRIPTION		"Services on this server are recommended to be moved out."
		::=  {  trap-alarm 30837}

-- 1.3.6.1.4.1.3902.6053.19.1.3.11.1.30837
    trap-30837-reasoninfo OBJECT IDENTIFIER ::= {trap-alarm 30837}

-- 1.3.6.1.4.1.3902.6053.19.1.3.11.1.30837.1
    trapServicesAreRecommendedToBeMovedOutInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30837-serialNumber, acTrapTime, acTrapEventSubject, acTrapSeverity, acTrapDescription, acTrapProductSerial, acTrapState, acTrapDeviceSN, acTrapAddInform, dwTrapIndex
		                                        }
		STATUS			current
		DESCRIPTION		"Services on this server are recommended to be moved out."
		::=  {  trap-30837-reasoninfo 1}
        
-- 1.3.6.1.4.1.3902.6053.19.1.3.11.1.30838
    trap-30838-addinfo OBJECT IDENTIFIER ::= {trap-addinfo 30838}

-- 1.3.6.1.4.1.3902.6053.19.1.3.11.2.30838.1
    trap-30838-dwCurrentValue OBJECT-TYPE
        SYNTAX Unsigned32
        ACCESS accessible-for-notify
        STATUS current
        DESCRIPTION 
            "Current Temperature"
        ::= {trap-30838-addinfo 1}

-- 1.3.6.1.4.1.3902.6053.19.1.3.11.2.30838.2
    trap-30838-dwThresholdValue OBJECT-TYPE
        SYNTAX Unsigned32
        ACCESS accessible-for-notify
        STATUS current
        DESCRIPTION 
            "Alert Temperature"
        ::= {trap-30838-addinfo 2}

-- 1.3.6.1.4.1.3902.6053.19.1.3.11.2.30838.3
    trap-30838-aucUnitStr OBJECT-TYPE
        SYNTAX DisplayString
        ACCESS accessible-for-notify
        STATUS current
        DESCRIPTION 
            "Unit"
        ::= {trap-30838-addinfo 3}
-- 1.3.6.1.4.1.3902.6053.19.1.3.11.1.30857
   trap-30857-addinfo OBJECT IDENTIFIER ::= {trap-addinfo 30857}
   
-- 1.3.6.1.4.1.3902.6053.19.1.3.11.2.30857.1
    trap-30857-ucIdeLocation OBJECT-TYPE
        SYNTAX Unsigned32
        ACCESS accessible-for-notify
        STATUS current
        DESCRIPTION 
            "Hard disk location"
        ::= {trap-30857-addinfo 1}
		
-- 1.3.6.1.4.1.3902.6053.19.1.3.11.2.30857.2
    trap-30857-ucIdeErrReason OBJECT-TYPE
        SYNTAX Unsigned32
        ACCESS accessible-for-notify
        STATUS current
        DESCRIPTION 
            "Hard disk abnormal reason"
        ::= {trap-30857-addinfo 2}

-- 1.3.6.1.4.1.3902.6053.19.1.3.11.2.30857.3
    trap-30857-ucZone OBJECT-TYPE
        SYNTAX Unsigned32
        ACCESS accessible-for-notify
        STATUS current
        DESCRIPTION 
            "Disk zone"
        ::= {trap-30857-addinfo 3}

-- 1.3.6.1.4.1.3902.6053.19.1.3.11.1.30857
    trapTheHardDiskTempIsHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30857-ucIdeLocation, trap-30857-ucIdeErrReason, trap-30857-ucZone, acTrapTime, acTrapEventSubject, acTrapSeverity, acTrapDescription, acTrapProductSerial, acTrapState, acTrapDeviceSN, acTrapAddInform, dwTrapIndex
		                                        }
		STATUS			current
		DESCRIPTION		"The hard disk temp is high."
		::=  {  trap-alarm 30857}

-- 1.3.6.1.4.1.3902.6053.19.1.3.11.1.30857
    trap-30857-reasoninfo OBJECT IDENTIFIER ::= {trap-alarm 30857}

-- 1.3.6.1.4.1.3902.6053.19.1.3.11.1.30857.1
    trapTheCommHardDiskTempIsHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30857-ucIdeLocation, trap-30857-ucIdeErrReason, trap-30857-ucZone, acTrapTime, acTrapEventSubject, acTrapSeverity, acTrapDescription, acTrapProductSerial, acTrapState, acTrapDeviceSN, acTrapAddInform, dwTrapIndex
		                                        }
		STATUS			current
		DESCRIPTION		"The hard disk temp is high."
		::=  {  trap-30857-reasoninfo 1} 

-- 1.3.6.1.4.1.3902.6053.19.1.3.11.1.30857.2
    trapTheFrontHardDiskTempIsHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30857-ucIdeLocation, trap-30857-ucIdeErrReason, trap-30857-ucZone, acTrapTime, acTrapEventSubject, acTrapSeverity, acTrapDescription, acTrapProductSerial, acTrapState, acTrapDeviceSN, acTrapAddInform, dwTrapIndex
		                                        }
		STATUS			current
		DESCRIPTION		"The hard disk temp is high."
		::=  {  trap-30857-reasoninfo 2} 

-- 1.3.6.1.4.1.3902.6053.19.1.3.11.1.30857.3
    trapTheRearHardDiskTempIsHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30857-ucIdeLocation, trap-30857-ucIdeErrReason, trap-30857-ucZone, acTrapTime, acTrapEventSubject, acTrapSeverity, acTrapDescription, acTrapProductSerial, acTrapState, acTrapDeviceSN, acTrapAddInform, dwTrapIndex
		                                        }
		STATUS			current
		DESCRIPTION		"The hard disk temp is high."
		::=  {  trap-30857-reasoninfo 3} 

-- 1.3.6.1.4.1.3902.6053.19.1.3.11.1.30857.4
    trapTheOsHardDiskTempIsHigh  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30857-ucIdeLocation, trap-30857-ucIdeErrReason, trap-30857-ucZone, acTrapTime, acTrapEventSubject, acTrapSeverity, acTrapDescription, acTrapProductSerial, acTrapState, acTrapDeviceSN, acTrapAddInform, dwTrapIndex
		                                        }
		STATUS			current
		DESCRIPTION		"The hard disk temp is high."
		::=  {  trap-30857-reasoninfo 4} 

-- 1.3.6.1.4.1.3902.6053.19.1.3.11.1.30838
    trapInletTemperatureIsHigherThanAlertTemperature  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30838-dwCurrentValue, trap-30838-dwThresholdValue, trap-30838-aucUnitStr, acTrapTime, acTrapEventSubject, acTrapSeverity, acTrapDescription, acTrapProductSerial, acTrapState, acTrapDeviceSN, acTrapAddInform, dwTrapIndex
		                                        }
		STATUS			current
		DESCRIPTION		"Device temperature is higher than alert temperature."
		::=  {  trap-alarm 30838}		

-- 1.3.6.1.4.1.3902.6053.19.1.3.11.1.30838
    trap-30838-reasoninfo OBJECT IDENTIFIER ::= {trap-alarm 30838}

-- 1.3.6.1.4.1.3902.6053.19.1.3.11.1.30838.1
    trapInletTemperatureIsHigherThanAlertTemperatureAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30838-dwCurrentValue, trap-30838-dwThresholdValue, trap-30838-aucUnitStr, acTrapTime, acTrapEventSubject, acTrapSeverity, acTrapDescription, acTrapProductSerial, acTrapState, acTrapDeviceSN, acTrapAddInform, dwTrapIndex
		                                        }
		STATUS			current
		DESCRIPTION		"Device temperature is higher than alert temperature."
		::=  {  trap-30838-reasoninfo 1}

-- 1.3.6.1.4.1.3902.6053.19.1.3.11.1.30839
    trap-30839-addinfo OBJECT IDENTIFIER ::= {trap-addinfo 30839}

-- 1.3.6.1.4.1.3902.6053.19.1.3.11.2.30839.1
    trap-30839-dwSensorNumber OBJECT-TYPE
        SYNTAX Unsigned32
        ACCESS accessible-for-notify
        STATUS current
        DESCRIPTION 
            "Sensor number"
        ::= {trap-30839-addinfo 1}

-- 1.3.6.1.4.1.3902.6053.19.1.3.11.1.30839
    trapInletTemperatureReadError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30839-dwSensorNumber, acTrapTime, acTrapEventSubject, acTrapSeverity, acTrapDescription, acTrapProductSerial, acTrapState, acTrapDeviceSN, acTrapAddInform, dwTrapIndex
		                                        }
		STATUS			current
		DESCRIPTION		"Abnormal reading of ambient temperature will affect the function of heat alert."
		::=  {  trap-alarm 30839}		

-- 1.3.6.1.4.1.3902.6053.19.1.3.11.1.30839
    trap-30839-reasoninfo OBJECT IDENTIFIER ::= {trap-alarm 30839}

-- 1.3.6.1.4.1.3902.6053.19.1.3.11.1.30839.1
    trapInletTemperatureReadErrorAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30839-dwSensorNumber, acTrapTime, acTrapEventSubject, acTrapSeverity, acTrapDescription, acTrapProductSerial, acTrapState, acTrapDeviceSN, acTrapAddInform, dwTrapIndex
		                                        }
		STATUS			current
		DESCRIPTION		"Abnormal reading of ambient temperature will affect the function of heat alert."
		::=  {  trap-30839-reasoninfo 1}

-- 1.3.6.1.4.1.3902.6053.19.1.3.11.1.30840
    trapPCIeTopoChange  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"PCIe topology changed."
		::=  {  trap-alarm 30840}

-- 1.3.6.1.4.1.3902.6053.19.1.3.11.1.30840
    trap-30840-reasoninfo OBJECT IDENTIFIER ::= {trap-alarm 30840}

-- 1.3.6.1.4.1.3902.6053.19.1.3.11.1.30840.1
    trapPCIeTopoStatusChange  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"PCIe topology changed."
		::=  {  trap-30840-reasoninfo 1}

-- 1.3.6.1.4.1.3902.6053.19.1.3.11.1.30841
    trapAutomaticApplyNewPCIeTopoChange  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"automatic apply new PCIe topology config."
		::=  {  trap-alarm 30841}
 
-- 1.3.6.1.4.1.3902.6053.19.1.3.11.1.30841
    trap-30841-reasoninfo OBJECT IDENTIFIER ::= {trap-alarm 30841}

-- 1.3.6.1.4.1.3902.6053.19.1.3.11.1.30841.1
    trapAutomaticApplyNewPCIeTopoChangeInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"automatic apply new PCIe topology config."
		::=  {  trap-30841-reasoninfo 1} 
       
-- 1.3.6.1.4.1.3902.6053.19.1.3.11.1.30842
    trap-30842-addinfo OBJECT IDENTIFIER ::= {trap-addinfo 30842}

-- 1.3.6.1.4.1.3902.6053.19.1.3.11.2.30842.1
    trap-30842-PcieSlot OBJECT-TYPE
        SYNTAX Unsigned32
        ACCESS accessible-for-notify
        STATUS current
        DESCRIPTION 
            "PCIE Slot"
        ::= {trap-30842-addinfo 1}

-- 1.3.6.1.4.1.3902.6053.19.1.3.11.1.30842
    trapPcieSlotEquipError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30842-PcieSlot, acTrapTime, acTrapEventSubject, acTrapSeverity, acTrapDescription, acTrapProductSerial, acTrapState, acTrapDeviceSN, acTrapAddInform, dwTrapIndex 
		                                        }

		STATUS			current
		DESCRIPTION		"PCIE slot equip error."
		::=  {  trap-alarm 30842}

-- 1.3.6.1.4.1.3902.6053.19.1.3.11.1.30842
    trap-30842-reasoninfo OBJECT IDENTIFIER ::= {trap-alarm 30842}

-- 1.3.6.1.4.1.3902.6053.19.1.3.11.1.30842.1
    trapPcieSlotEquipErrorAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30842-PcieSlot, acTrapTime, acTrapEventSubject, acTrapSeverity, acTrapDescription, acTrapProductSerial, acTrapState, acTrapDeviceSN, acTrapAddInform, dwTrapIndex 
		                                        }

		STATUS			current
		DESCRIPTION		"PCIE slot equip error."
		::=  {  trap-30842-reasoninfo 1}
       
-- 1.3.6.1.4.1.3902.6053.19.1.3.11.1.30843
    trap-30843-addinfo OBJECT IDENTIFIER ::= {trap-addinfo 30843}

-- 1.3.6.1.4.1.3902.6053.19.1.3.11.2.30843.1
    trap-30843-ucIdeLocation OBJECT-TYPE
        SYNTAX Unsigned32
        ACCESS accessible-for-notify
        STATUS current
        DESCRIPTION 
            "Hard disk location"
        ::= {trap-30843-addinfo 1}

-- 1.3.6.1.4.1.3902.6053.19.1.3.11.1.30843
    trapTheHardDiskIsMissing  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is missing."
		::=  {  trap-alarm 30843}

-- 1.3.6.1.4.1.3902.6053.19.1.3.11.1.30843
    trap-30843-reasoninfo OBJECT IDENTIFIER ::= {trap-alarm 30843}

-- 1.3.6.1.4.1.3902.6053.19.1.3.11.1.30843.1
    trapTheCommHardDiskIsMissing  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is missing."
		::=  {  trap-30843-reasoninfo 1}

-- 1.3.6.1.4.1.3902.6053.19.1.3.11.1.30843.2
    trapTheFrontHardDiskIsMissing  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is missing."
		::=  {  trap-30843-reasoninfo 2}

-- 1.3.6.1.4.1.3902.6053.19.1.3.11.1.30843.3
    trapTheRearHardDiskIsMissing  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is missing."
		::=  {  trap-30843-reasoninfo 3}

-- 1.3.6.1.4.1.3902.6053.19.1.3.11.1.30843.4
    trapTheOsHardDiskIsMissing  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is missing."
		::=  {  trap-30843-reasoninfo 4}

-- 1.3.6.1.4.1.3902.6053.19.1.3.11.1.30844
    trap-30844-addinfo OBJECT IDENTIFIER ::= {trap-addinfo 30844}

-- 1.3.6.1.4.1.3902.6053.19.1.3.11.2.30844.1
    trap-30844-ucIdeLocation OBJECT-TYPE
        SYNTAX Unsigned32
        ACCESS accessible-for-notify
        STATUS current
        DESCRIPTION 
            "Hard disk location"
        ::= {trap-30844-addinfo 1}

-- 1.3.6.1.4.1.3902.6053.19.1.3.11.1.30844
    trapTheHardDiskIsNotAccessible  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is not accessible."
		::=  {  trap-alarm 30844}

-- 1.3.6.1.4.1.3902.6053.19.1.3.11.1.30844
    trap-30844-reasoninfo OBJECT IDENTIFIER ::= {trap-alarm 30844}

-- 1.3.6.1.4.1.3902.6053.19.1.3.11.1.30844.1
    trapTheCommHardDiskIsNotAccessible  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is not accessible."
		::=  {  trap-30844-reasoninfo 1}

-- 1.3.6.1.4.1.3902.6053.19.1.3.11.1.30844.2
    trapTheFrontHardDiskIsNotAccessible  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is not accessible."
		::=  {  trap-30844-reasoninfo 2}

-- 1.3.6.1.4.1.3902.6053.19.1.3.11.1.30844.3
    trapTheRearHardDiskIsNotAccessible  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is not accessible."
		::=  {  trap-30844-reasoninfo 3}

-- 1.3.6.1.4.1.3902.6053.19.1.3.11.1.30844.4
    trapTheOsHardDiskIsNotAccessible  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30843-ucIdeLocation, acTrapTime, acTrapEventSubject, acTrapSeverity, acTrapDescription, acTrapProductSerial, acTrapState, acTrapDeviceSN, acTrapAddInform, dwTrapIndex
		                                        }
		STATUS			current
		DESCRIPTION		"The hard disk is not accessible."
		::=  {  trap-30844-reasoninfo 4}

-- 1.3.6.1.4.1.3902.6053.19.1.3.11.1.30860
    trap-30860-addinfo OBJECT IDENTIFIER ::= {trap-addinfo 30860}

-- 1.3.6.1.4.1.3902.6053.19.1.3.11.2.30860.1
    trap-30860-ucIdeLocation OBJECT-TYPE
        SYNTAX Unsigned32
        ACCESS accessible-for-notify
        STATUS current
        DESCRIPTION 
            "Hard disk location"
        ::= {trap-30860-addinfo 1}

-- 1.3.6.1.4.1.3902.6053.19.1.3.11.2.30860.2
    trap-30860-ucIdeErrReason OBJECT-TYPE
        SYNTAX Unsigned32
        {
            unknown(0),
            nvme-remaining-life-insufficient(12),
            hard-disk-status-abnormal(13),
            smart-parameter-exceeds-threshold(14)
        }
        ACCESS accessible-for-notify
        STATUS current
        DESCRIPTION
            "Hard disk error reason"
        ::= {trap-30860-addinfo 2}

-- 1.3.6.1.4.1.3902.6053.19.1.3.11.2.30860.3
    trap-30860-ucZone OBJECT-TYPE
        SYNTAX Unsigned32
        {
            null(0),
            front-panel(1),
            rear-panel(2),
            system(3)
        }
        ACCESS accessible-for-notify
        STATUS current
        DESCRIPTION
            "Hard disk alarm area of slot"
        ::= {trap-30860-addinfo 3}

-- 1.3.6.1.4.1.3902.6053.19.1.3.11.1.30860
    trapTheHardDiskInPrefailureStatus   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has predictive failure."
        ::=  {  trap-alarm 30860}

-- 1.3.6.1.4.1.3902.6053.19.1.3.11.1.30860
    trap-30860-reasoninfo OBJECT IDENTIFIER ::= {trap-alarm 30860}

-- 1.3.6.1.4.1.3902.6053.19.1.3.11.1.30860.1
    trapTheCommHardDiskInPrefailureStatus   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has predictive failure."
        ::=  {  trap-30860-reasoninfo 1}

-- 1.3.6.1.4.1.3902.6053.19.1.3.11.1.30860.2
    trapTheFrontHardDiskInPrefailureStatus   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has predictive failure."
        ::=  {  trap-30860-reasoninfo 2}

-- 1.3.6.1.4.1.3902.6053.19.1.3.11.1.30860.3
    trapTheRearHardDiskInPrefailureStatus   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has predictive failure."
        ::=  {  trap-30860-reasoninfo 3}

-- 1.3.6.1.4.1.3902.6053.19.1.3.11.1.30860.4
    trapTheOsHardDiskInPrefailureStatus   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has predictive failure."
        ::=  {  trap-30860-reasoninfo 4}

-- 1.3.6.1.4.1.3902.6053.19.1.3.11.1.30918
    trap-30918-addinfo OBJECT IDENTIFIER ::= {trap-addinfo 30918}

-- 1.3.6.1.4.1.3902.6053.19.1.3.11.2.30918.1
    trap-30918-ucIdeLocation OBJECT-TYPE
        SYNTAX Unsigned32
        ACCESS accessible-for-notify
        STATUS current
        DESCRIPTION 
            "Hard disk location"
        ::= {trap-30918-addinfo 1}

-- 1.3.6.1.4.1.3902.6053.19.1.3.11.2.30918.2
    trap-30918-ucIdeErrReason OBJECT-TYPE
        SYNTAX Unsigned32
        {
            unknown(0),
            foreign-configuration(17)
        }
        ACCESS accessible-for-notify
        STATUS current
        DESCRIPTION
            "Hard disk error reason"
        ::= {trap-30918-addinfo 2}

-- 1.3.6.1.4.1.3902.6053.19.1.3.11.2.30918.3
    trap-30918-ucZone OBJECT-TYPE
        SYNTAX Unsigned32
        {
            null(0),
            front-panel(1),
            rear-panel(2),
            system(3)
        }
        ACCESS accessible-for-notify
        STATUS current
        DESCRIPTION
            "Hard disk alarm area of slot"
        ::= {trap-30918-addinfo 3}


-- 1.3.6.1.4.1.3902.6053.19.1.3.11.1.30918
    trapTheHardDiskPDLIsLow   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has foreign configuration."
        ::=  {  trap-alarm 30918}

-- 1.3.6.1.4.1.3902.6053.19.1.3.11.1.30918
    trap-30918-reasoninfo OBJECT IDENTIFIER ::= {trap-alarm 30918}

-- 1.3.6.1.4.1.3902.6053.19.1.3.11.1.30918.1
    trapTheCommHardDiskPDLIsLow   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has foreign configuration."
        ::=  {  trap-30918-reasoninfo 1}

-- 1.3.6.1.4.1.3902.6053.19.1.3.11.1.30918.2
    trapTheFrontHardDiskPDLIsLow   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has foreign configuration."
        ::=  {  trap-30918-reasoninfo 2}

-- 1.3.6.1.4.1.3902.6053.19.1.3.11.1.30918.3
    trapTheRearHardDiskPDLIsLow   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has foreign configuration."
        ::=  {  trap-30918-reasoninfo 3}

-- 1.3.6.1.4.1.3902.6053.19.1.3.11.1.30918.4
    trapTheOsHardDiskPDLIsLow   NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30860-ucIdeLocation, trap-30860-ucIdeErrReason, trap-30860-ucZone, acTrapTime, acTrapEventSubject, acTrapSeverity, acTrapDescription, acTrapProductSerial, acTrapState, acTrapDeviceSN, acTrapAddInform, dwTrapIndex
                                                }
        STATUS          current
        DESCRIPTION     "The hard disk has foreign configuration."
        ::=  {  trap-30918-reasoninfo 4}
		
-- 1.3.6.1.4.1.3902.6053.19.1.3.11.1.30845
    trapWatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-alarm 30845}

-- 1.3.6.1.4.1.3902.6053.19.1.3.11.1.30845
    trap-30845-reasoninfo OBJECT IDENTIFIER ::= {trap-alarm 30845}

-- 1.3.6.1.4.1.3902.6053.19.1.3.11.1.30845.1
    trapBIOSorFRB2WatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 1}

-- 1.3.6.1.4.1.3902.6053.19.1.3.11.1.30845.2
    trapBIOSorPOSTWatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 2}

-- 1.3.6.1.4.1.3902.6053.19.1.3.11.1.30845.3
    trapOsResetBIOSorFRB2WatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 3}

-- 1.3.6.1.4.1.3902.6053.19.1.3.11.1.30845.4
    trapOsResetBIOSorPOSTWatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 4}

-- 1.3.6.1.4.1.3902.6053.19.1.3.11.1.30845.5
    trapOsPoweredOffBIOSorFRB2WatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 5}
		
-- 1.3.6.1.4.1.3902.6053.19.1.3.11.1.30845.6
    trapOsPoweredOffBIOSorPOSTWatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 6}

-- 1.3.6.1.4.1.3902.6053.19.1.3.11.1.30845.7
    trapOsPoweredOffAndOnBIOSorFRB2WatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 7}

-- 1.3.6.1.4.1.3902.6053.19.1.3.11.1.30845.8
    trapOsPoweredOffAndOnBIOSorPOSTWatchDogAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog alarm."
		::=  {  trap-30845-reasoninfo 8}
		
-- 1.3.6.1.4.1.3902.6053.19.1.3.11.1.30846
    trapWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-alarm 30846}				

-- 1.3.6.1.4.1.3902.6053.19.1.3.11.1.30846
    trap-30846-reasoninfo OBJECT IDENTIFIER ::= {trap-alarm 30846}

-- 1.3.6.1.4.1.3902.6053.19.1.3.11.1.30846.1
    trapOsLoadWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 1}

-- 1.3.6.1.4.1.3902.6053.19.1.3.11.1.30846.2
    trapSMSorOSWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 2}
		
-- 1.3.6.1.4.1.3902.6053.19.1.3.11.1.30846.3
    trapOsResetOsLoadWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 3}

-- 1.3.6.1.4.1.3902.6053.19.1.3.11.1.30846.4
    trapOsResetSMSorOSWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 4}
		
-- 1.3.6.1.4.1.3902.6053.19.1.3.11.1.30846.5
    trapOsPoweredOffOsLoadWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 5}
		
-- 1.3.6.1.4.1.3902.6053.19.1.3.11.1.30846.6
    trapOsPoweredOffSMSorOSWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 6}

-- 1.3.6.1.4.1.3902.6053.19.1.3.11.1.30846.7
    trapOsPoweredOffAndOnOsLoadWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 7}
		
-- 1.3.6.1.4.1.3902.6053.19.1.3.11.1.30846.8
    trapOsPoweredOffAndOnSMSorOSWatchDogInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"watchdog info."
		::=  {  trap-30846-reasoninfo 8}	
      
-- 1.3.6.1.4.1.3902.6053.19.1.3.11.1.30852
    trap-30852-addinfo OBJECT IDENTIFIER ::= {trap-addinfo 30852}

-- 1.3.6.1.4.1.3902.6053.19.1.3.11.2.30852.1
    trap-30852-aucSensorName OBJECT-TYPE
        SYNTAX DisplayString
        ACCESS accessible-for-notify
        STATUS current
        DESCRIPTION 
            "Sensor Name"
        ::= {trap-30852-addinfo 1}
	
-- 1.3.6.1.4.1.3902.6053.19.1.3.11.1.30852
    trapUidButtonInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30852-aucSensorName, acTrapTime, acTrapEventSubject, acTrapSeverity, acTrapDescription, acTrapProductSerial, acTrapState, acTrapDeviceSN, acTrapAddInform, dwTrapIndex
		                                        }
		STATUS			current
		DESCRIPTION		"UID button is pressed down."
		::=  {  trap-alarm 30852}

-- 1.3.6.1.4.1.3902.6053.19.1.3.11.1.30852
    trap-30852-reasoninfo OBJECT IDENTIFIER ::= {trap-alarm 30852}

-- 1.3.6.1.4.1.3902.6053.19.1.3.11.1.30852.1
    trapUidButtonPressedDownInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30852-aucSensorName, acTrapTime, acTrapEventSubject, acTrapSeverity, acTrapDescription, acTrapProductSerial, acTrapState, acTrapDeviceSN, acTrapAddInform, dwTrapIndex
		                                        }
		STATUS			current
		DESCRIPTION		"UID button is pressed down."
		::=  {  trap-30852-reasoninfo 1}
	
-- 1.3.6.1.4.1.3902.6053.19.1.3.11.1.30853
    trap-30853-addinfo OBJECT IDENTIFIER ::= {trap-addinfo 30853}

-- 1.3.6.1.4.1.3902.6053.19.1.3.11.2.30853.1
    trap-30853-aucSensorName OBJECT-TYPE
        SYNTAX DisplayString
        ACCESS accessible-for-notify
        STATUS current
        DESCRIPTION 
            "Sensor Name"
        ::= {trap-30853-addinfo 1}
		
-- 1.3.6.1.4.1.3902.6053.19.1.3.11.2.30853.2
    trap-30853-ucResetType OBJECT-TYPE
        SYNTAX Unsigned32
        ACCESS accessible-for-notify
        STATUS current
        DESCRIPTION 
            "Reset Type"
        ::= {trap-30853-addinfo 2}
		
-- 1.3.6.1.4.1.3902.6053.19.1.3.11.1.30853
    trapBmcSystemRestart  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30853-aucSensorName, trap-30853-ucResetType, acTrapTime, acTrapEventSubject, acTrapSeverity, acTrapDescription, acTrapProductSerial, acTrapState, acTrapDeviceSN, acTrapAddInform, dwTrapIndex
		                                        }
		STATUS			current
		DESCRIPTION		"BMC system is restart complteted."
		::=  {  trap-alarm 30853}	

-- 1.3.6.1.4.1.3902.6053.19.1.3.11.1.30853
    trap-30853-reasoninfo OBJECT IDENTIFIER ::= {trap-alarm 30853}

-- 1.3.6.1.4.1.3902.6053.19.1.3.11.1.30853.1
    trapBmcSystemRestartCompleted  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30853-aucSensorName, trap-30853-ucResetType, acTrapTime, acTrapEventSubject, acTrapSeverity, acTrapDescription, acTrapProductSerial, acTrapState, acTrapDeviceSN, acTrapAddInform, dwTrapIndex
		                                        }
		STATUS			current
		DESCRIPTION		"BMC system is restart complteted."
		::=  {  trap-30853-reasoninfo 1}

-- 1.3.6.1.4.1.3902.6053.19.1.3.11.1.30854
    trap-30854-addinfo OBJECT IDENTIFIER ::= {trap-addinfo 30854}

-- 1.3.6.1.4.1.3902.6053.19.1.3.11.2.30854.1
    trap-30854-aucSensorName OBJECT-TYPE
        SYNTAX DisplayString
        ACCESS accessible-for-notify
        STATUS current
        DESCRIPTION
            "Sensor Name"
        ::= {trap-30854-addinfo 1}

-- 1.3.6.1.4.1.3902.6053.19.1.3.11.1.30854
    trapPowerButtonInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30854-aucSensorName, trap-30854-ucResetType, acTrapTime, acTrapEventSubject, acTrapSeverity, acTrapDescription, acTrapProductSerial, acTrapState, acTrapDeviceSN, acTrapAddInform, dwTrapIndex
		                                        }
		STATUS			current
		DESCRIPTION		"Power button is pressed down."
		::=  {  trap-alarm 30854}

-- 1.3.6.1.4.1.3902.6053.19.1.3.11.1.30854
    trap-30854-reasoninfo OBJECT IDENTIFIER ::= {trap-alarm 30854}

-- 1.3.6.1.4.1.3902.6053.19.1.3.11.1.30854.1
    trapPowerButtonPressedDownInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30854-aucSensorName, trap-30854-ucResetType, acTrapTime, acTrapEventSubject, acTrapSeverity, acTrapDescription, acTrapProductSerial, acTrapState, acTrapDeviceSN, acTrapAddInform, dwTrapIndex
		                                        }
		STATUS			current
		DESCRIPTION		"Power button is pressed down."
		::=  {  trap-30854-reasoninfo 1} 

-- 1.3.6.1.4.1.3902.6053.19.1.3.11.1.65535
    trapTest  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                       }
		STATUS			current
		DESCRIPTION		"trap test."
		::=  {  trap-alarm 65535}

-- 1.3.6.1.4.1.3902.6053.19.1.3.11.1.65535
    trap-65535-reasoninfo OBJECT IDENTIFIER ::= {trap-alarm 65535}

-- 1.3.6.1.4.1.3902.6053.19.1.3.11.1.65535.0
    trapTestInfo  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                       }
		STATUS			current
		DESCRIPTION		"trap test."
		::=  {  trap-65535-reasoninfo 0}

-- 1.3.6.1.4.1.3902.6053.19.1.3.11.1.30847
    trap-30847-addinfo OBJECT IDENTIFIER ::= {trap-addinfo 30847}

-- 1.3.6.1.4.1.3902.6053.19.1.3.11.2.30847.1
    trap-30847-ucStatus OBJECT-TYPE
        SYNTAX Unsigned32
        ACCESS accessible-for-notify
        STATUS current
        DESCRIPTION 
            "Status"
        ::= {trap-30847-addinfo 1}
		
-- 1.3.6.1.4.1.3902.6053.19.1.3.11.2.30847.2
    trap-30847-aucSensorName OBJECT-TYPE
        SYNTAX DisplayString
        ACCESS accessible-for-notify
        STATUS current
        DESCRIPTION 
            "Sensor Name"
        ::= {trap-30847-addinfo 2}

-- 1.3.6.1.4.1.3902.6053.19.1.3.11.1.30847
    trapFanFullyRedundant  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30847-ucStatus,trap-30847-aucSensorName, acTrapTime, acTrapEventSubject, acTrapSeverity, acTrapDescription, acTrapProductSerial, acTrapState, acTrapDeviceSN, acTrapAddInform, dwTrapIndex
		                                        }
		STATUS			current
		DESCRIPTION		"Fan fully redundant state"
		::=  {  trap-alarm 30847}

-- 1.3.6.1.4.1.3902.6053.19.1.3.11.1.30847
    trap-30847-reasoninfo OBJECT IDENTIFIER ::= {trap-alarm 30847}

-- 1.3.6.1.4.1.3902.6053.19.1.3.11.1.30847.1
    trapFanStatusFullyRedundant  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30847-ucStatus,trap-30847-aucSensorName, acTrapTime, acTrapEventSubject, acTrapSeverity, acTrapDescription, acTrapProductSerial, acTrapState, acTrapDeviceSN, acTrapAddInform, dwTrapIndex
		                                        }
		STATUS			current
		DESCRIPTION		"Fan fully redundant state"
		::=  {  trap-30847-reasoninfo 1}

-- 1.3.6.1.4.1.3902.6053.19.1.3.11.1.30848
    trap-30848-addinfo OBJECT IDENTIFIER ::= {trap-addinfo 30848}

-- 1.3.6.1.4.1.3902.6053.19.1.3.11.2.30848.1
    trap-30848-ucStatus OBJECT-TYPE
        SYNTAX Unsigned32
        ACCESS accessible-for-notify
        STATUS current
        DESCRIPTION 
            "Status"
        ::= {trap-30848-addinfo 1}
		
-- 1.3.6.1.4.1.3902.6053.19.1.3.11.2.30848.2
    trap-30848-aucSensorName OBJECT-TYPE
        SYNTAX DisplayString
        ACCESS accessible-for-notify
        STATUS current
        DESCRIPTION 
            "Sensor Name"
        ::= {trap-30848-addinfo 2}

-- 1.3.6.1.4.1.3902.6053.19.1.3.11.1.30848
    trapFanRedundancyLost  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30848-ucStatus,trap-30848-aucSensorName, acTrapTime, acTrapEventSubject, acTrapSeverity, acTrapDescription, acTrapProductSerial, acTrapState, acTrapDeviceSN, acTrapAddInform, dwTrapIndex
		                                        }
		STATUS			current
		DESCRIPTION		"Fan redundancy lost state"
		::=  {  trap-alarm 30848}

-- 1.3.6.1.4.1.3902.6053.19.1.3.11.1.30848
    trap-30848-reasoninfo OBJECT IDENTIFIER ::= {trap-alarm 30848}

-- 1.3.6.1.4.1.3902.6053.19.1.3.11.1.30848.1
    trapFanStatusRedundancyLost  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30848-ucStatus,trap-30848-aucSensorName, acTrapTime, acTrapEventSubject, acTrapSeverity, acTrapDescription, acTrapProductSerial, acTrapState, acTrapDeviceSN, acTrapAddInform, dwTrapIndex
		                                        }
		STATUS			current
		DESCRIPTION		"Fan redundancy lost state"
		::=  {  trap-30848-reasoninfo 1}

-- 1.3.6.1.4.1.3902.6053.19.1.3.11.1.30849
    trap-30849-addinfo OBJECT IDENTIFIER ::= {trap-addinfo 30849}

-- 1.3.6.1.4.1.3902.6053.19.1.3.11.2.30849.1
    trap-30849-ucStatus OBJECT-TYPE
        SYNTAX Unsigned32
        ACCESS accessible-for-notify
        STATUS current
        DESCRIPTION 
            "Status"
        ::= {trap-30849-addinfo 1}
		
-- 1.3.6.1.4.1.3902.6053.19.1.3.11.2.30849.2
    trap-30849-aucSensorName OBJECT-TYPE
        SYNTAX DisplayString
        ACCESS accessible-for-notify
        STATUS current
        DESCRIPTION 
            "Sensor Name"
        ::= {trap-30849-addinfo 2}

-- 1.3.6.1.4.1.3902.6053.19.1.3.11.1.30849
    trapPSUFullyRedundant  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30849-ucStatus,trap-30849-aucSensorName, acTrapTime, acTrapEventSubject, acTrapSeverity, acTrapDescription, acTrapProductSerial, acTrapState, acTrapDeviceSN, acTrapAddInform, dwTrapIndex
		                                        }
		STATUS			current
		DESCRIPTION		"PSU fully redundanct state"
		::=  {  trap-alarm 30849}

-- 1.3.6.1.4.1.3902.6053.19.1.3.11.1.30849
    trap-30849-reasoninfo OBJECT IDENTIFIER ::= {trap-alarm 30849}

-- 1.3.6.1.4.1.3902.6053.19.1.3.11.1.30849.1
    trapPSUStatusFullyRedundant  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30849-ucStatus,trap-30849-aucSensorName, acTrapTime, acTrapEventSubject, acTrapSeverity, acTrapDescription, acTrapProductSerial, acTrapState, acTrapDeviceSN, acTrapAddInform, dwTrapIndex
		                                        }
		STATUS			current
		DESCRIPTION		"PSU fully redundanct state"
		::=  {  trap-30849-reasoninfo 1}

-- 1.3.6.1.4.1.3902.6053.19.1.3.11.1.30850
    trap-30850-addinfo OBJECT IDENTIFIER ::= {trap-addinfo 30850}

-- 1.3.6.1.4.1.3902.6053.19.1.3.11.2.30850.1
    trap-30850-ucStatus OBJECT-TYPE
        SYNTAX Unsigned32
        ACCESS accessible-for-notify
        STATUS current
        DESCRIPTION 
            "Status"
        ::= {trap-30850-addinfo 1}
		
-- 1.3.6.1.4.1.3902.6053.19.1.3.11.2.30850.2
    trap-30850-aucSensorName OBJECT-TYPE
        SYNTAX DisplayString
        ACCESS accessible-for-notify
        STATUS current
        DESCRIPTION 
            "Sensor Name"
        ::= {trap-30850-addinfo 2}

-- 1.3.6.1.4.1.3902.6053.19.1.3.11.1.30850
    trapPSURedundancyDegraded  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30850-ucStatus,trap-30850-aucSensorName, acTrapTime, acTrapEventSubject, acTrapSeverity, acTrapDescription, acTrapProductSerial, acTrapState, acTrapDeviceSN, acTrapAddInform, dwTrapIndex
		                                        }
		STATUS			current
		DESCRIPTION		"PSU redundancy degraded state"
		::=  {  trap-alarm 30850}

-- 1.3.6.1.4.1.3902.6053.19.1.3.11.1.30850
    trap-30850-reasoninfo OBJECT IDENTIFIER ::= {trap-alarm 30850}

-- 1.3.6.1.4.1.3902.6053.19.1.3.11.1.30850.1
    trapPSUStatusRedundancyDegraded  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30850-ucStatus,trap-30850-aucSensorName, acTrapTime, acTrapEventSubject, acTrapSeverity, acTrapDescription, acTrapProductSerial, acTrapState, acTrapDeviceSN, acTrapAddInform, dwTrapIndex
		                                        }
		STATUS			current
		DESCRIPTION		"PSU redundancy degraded state"
		::=  {  trap-30850-reasoninfo 1}

-- 1.3.6.1.4.1.3902.6053.19.1.3.11.1.30851
    trap-30851-addinfo OBJECT IDENTIFIER ::= {trap-addinfo 30851}

-- 1.3.6.1.4.1.3902.6053.19.1.3.11.2.30851.1
    trap-30851-ucStatus OBJECT-TYPE
        SYNTAX Unsigned32
        ACCESS accessible-for-notify
        STATUS current
        DESCRIPTION 
            "Status"
        ::= {trap-30851-addinfo 1}
		
-- 1.3.6.1.4.1.3902.6053.19.1.3.11.2.30851.2
    trap-30851-aucSensorName OBJECT-TYPE
        SYNTAX DisplayString
        ACCESS accessible-for-notify
        STATUS current
        DESCRIPTION 
            "Sensor Name"
        ::= {trap-30851-addinfo 2}

-- 1.3.6.1.4.1.3902.6053.19.1.3.11.1.30851
    trapPSURedundancyLost  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30851-ucStatus,trap-30851-aucSensorName, acTrapTime, acTrapEventSubject, acTrapSeverity, acTrapDescription, acTrapProductSerial, acTrapState, acTrapDeviceSN, acTrapAddInform, dwTrapIndex
		                                        }
		STATUS			current
		DESCRIPTION		"PSU redundancy lost state"
		::=  {  trap-alarm 30851}

-- 1.3.6.1.4.1.3902.6053.19.1.3.11.1.30851
    trap-30851-reasoninfo OBJECT IDENTIFIER ::= {trap-alarm 30851}

-- 1.3.6.1.4.1.3902.6053.19.1.3.11.1.30851.1
    trapPSUStatusRedundancyLost  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30851-ucStatus,trap-30851-aucSensorName, acTrapTime, acTrapEventSubject, acTrapSeverity, acTrapDescription, acTrapProductSerial, acTrapState, acTrapDeviceSN, acTrapAddInform, dwTrapIndex
		                                        }
		STATUS			current
		DESCRIPTION		"PSU redundancy lost state"
		::=  {  trap-30851-reasoninfo 1}

-- 1.3.6.1.4.1.3902.6053.19.1.3.11.1.30856
    trap-30856-addinfo OBJECT IDENTIFIER ::= {trap-addinfo 30856}

-- 1.3.6.1.4.1.3902.6053.19.1.3.11.2.30856.1
    trap-30856-aucSensorName OBJECT-TYPE
        SYNTAX DisplayString
        ACCESS accessible-for-notify
        STATUS current
        DESCRIPTION 
            "Sensor Name"
        ::= {trap-30856-addinfo 1}
		
-- 1.3.6.1.4.1.3902.6053.19.1.3.11.2.30856.2
    trap-30856-ucResetType OBJECT-TYPE
        SYNTAX Unsigned32
        ACCESS accessible-for-notify
        STATUS current
        DESCRIPTION 
            "Reset Type"
        ::= {trap-30856-addinfo 2}
		
-- 1.3.6.1.4.1.3902.6053.19.1.3.11.1.30856
    trapSystemBoot  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30856-aucSensorName, trap-30856-ucResetType, acTrapTime, acTrapEventSubject, acTrapSeverity, acTrapDescription, acTrapProductSerial, acTrapState, acTrapDeviceSN, acTrapAddInform, dwTrapIndex
		                                        }
		STATUS			current
		DESCRIPTION		"System boot/restart initiated."
		::=  {  trap-alarm 30856}

-- 1.3.6.1.4.1.3902.6053.19.1.3.11.1.30856
    trap-30856-reasoninfo OBJECT IDENTIFIER ::= {trap-alarm 30856}

-- 1.3.6.1.4.1.3902.6053.19.1.3.11.1.30856.1
    trapSystemBootByPowerUp  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30856-aucSensorName, trap-30856-ucResetType, acTrapTime, acTrapEventSubject, acTrapSeverity, acTrapDescription, acTrapProductSerial, acTrapState, acTrapDeviceSN, acTrapAddInform, dwTrapIndex
		                                        }
		STATUS			current
		DESCRIPTION		"System boot/restart initiated."
		::=  {  trap-30856-reasoninfo 1}

-- 1.3.6.1.4.1.3902.6053.19.1.3.11.1.30856.2
    trapSystemBootByHardReset  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30856-aucSensorName, trap-30856-ucResetType, acTrapTime, acTrapEventSubject, acTrapSeverity, acTrapDescription, acTrapProductSerial, acTrapState, acTrapDeviceSN, acTrapAddInform, dwTrapIndex
		                                        }
		STATUS			current
		DESCRIPTION		"System boot/restart initiated."
		::=  {  trap-30856-reasoninfo 2} 
		
-- 1.3.6.1.4.1.3902.6053.19.1.3.11.1.30856.3
    trapSystemBootByWarmReset  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30856-aucSensorName, trap-30856-ucResetType, acTrapTime, acTrapEventSubject, acTrapSeverity, acTrapDescription, acTrapProductSerial, acTrapState, acTrapDeviceSN, acTrapAddInform, dwTrapIndex
		                                        }
		STATUS			current
		DESCRIPTION		"System boot/restart initiated."
		::=  {  trap-30856-reasoninfo 3} 
		
-- 1.3.6.1.4.1.3902.6053.19.1.3.11.1.30856.4
    trapSystemBootBySystemRestart  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30856-aucSensorName, trap-30856-ucResetType, acTrapTime, acTrapEventSubject, acTrapSeverity, acTrapDescription, acTrapProductSerial, acTrapState, acTrapDeviceSN, acTrapAddInform, dwTrapIndex
		                                        }
		STATUS			current
		DESCRIPTION		"System boot/restart initiated."
		::=  {  trap-30856-reasoninfo 4}
		
-- 1.3.6.1.4.1.3902.6053.19.1.3.11.1.30859
    trap-30859-addinfo OBJECT IDENTIFIER ::= {trap-addinfo 30859}
	
-- 1.3.6.1.4.1.3902.6053.19.1.3.11.1.30859.1
    trap-30859-slot OBJECT-TYPE
        SYNTAX Unsigned32
        ACCESS accessible-for-notify
        STATUS current
        DESCRIPTION 
            "Slot"
        ::= {trap-30859-addinfo 1}

-- 1.3.6.1.4.1.3902.6053.19.1.3.11.1.30859
    trapSmartNicDetectError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Smart Nic Detect Error."
		::=  {  trap-alarm 30859}

-- 1.3.6.1.4.1.3902.6053.19.1.3.11.1.30859
    trap-30859-reasoninfo OBJECT IDENTIFIER ::= {trap-alarm 30859}

-- 1.3.6.1.4.1.3902.6053.19.1.3.11.1.30859.1
    trapSmartNicDetectErrorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Smart Nic Detect Error."
		::=  {  trap-30859-reasoninfo 1}

-- 1.3.6.1.4.1.3902.6053.19.1.3.11.1.8392707
    trap-8392707-addinfo OBJECT IDENTIFIER ::= {trap-addinfo 8392707}

-- 1.3.6.1.4.1.3902.6053.19.1.3.11.1.8392707
    trapNtpSynchronizationEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"BMC synchronization status is changed."
		::=  {  trap-alarm 8392707}

-- 1.3.6.1.4.1.3902.6053.19.1.3.11.1.8392707
    trap-8392707-reasoninfo OBJECT IDENTIFIER ::= {trap-alarm 8392707}

-- 1.3.6.1.4.1.3902.6053.19.1.3.11.1.8392707.1
    trapNtpFailedSynchronizationEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"BMC synchronization status is changed."
		::=  {  trap-8392707-reasoninfo 1}
		
-- 1.3.6.1.4.1.3902.6053.19.1.3.11.1.8392707.2
    trapNtpSuccessedSynchronizationEvent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"BMC synchronization status is changed."
		::=  {  trap-8392707-reasoninfo 2}

-- 1.3.6.1.4.1.3902.6053.19.1.3.11.1.30861
    trap-30861-addinfo OBJECT IDENTIFIER ::= {trap-addinfo 30861}

-- 1.3.6.1.4.1.3902.6053.19.1.3.11.1.30861
    liquidSystemLeakage  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Liquid cooling system is leaking."
		::=  {  trap-alarm 30861}	

-- 1.3.6.1.4.1.3902.6053.19.1.3.11.1.30861
    trap-30861-reasoninfo OBJECT IDENTIFIER ::= {trap-alarm 30861}

-- 1.3.6.1.4.1.3902.6053.19.1.3.11.1.30861.1
    liquidSystemLeakageAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Liquid cooling system is leaking."
		::=  {  trap-30861-reasoninfo 1}

-- 1.3.6.1.4.1.3902.6053.19.1.3.11.1.30862
    trap-30862-addinfo OBJECT IDENTIFIER ::= {trap-addinfo 30862}

-- 1.3.6.1.4.1.3902.6053.19.1.3.11.1.30862
    liquidLeakageLineFault  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Liquid cooling system is out of service."
		::=  {  trap-alarm 30862}	

-- 1.3.6.1.4.1.3902.6053.19.1.3.11.1.30862
    trap-30862-reasoninfo OBJECT IDENTIFIER ::= {trap-alarm 30862}

-- 1.3.6.1.4.1.3902.6053.19.1.3.11.1.30862.1
    liquidLeakageLineFaultAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Liquid cooling system is out of service."
		::=  {  trap-30862-reasoninfo 1}	

-- 1.3.6.1.4.1.3902.6053.19.1.3.11.1.30864
    trap-30864-addinfo OBJECT IDENTIFIER ::= {trap-addinfo 30864}
	
-- 1.3.6.1.4.1.3902.6053.19.1.3.11.1.30864
    trapFanSpeedStatusAbnormalAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Fan speed status abnormal alarm."
		::=  {  trap-alarm 30864}

-- 1.3.6.1.4.1.3902.6053.19.1.3.11.1.30864
    trap-30864-reasoninfo OBJECT IDENTIFIER ::= {trap-alarm 30864}

-- 1.3.6.1.4.1.3902.6053.19.1.3.11.1.30864.1
    trapFanSpeedStatusAbnormalBySensorAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Fan speed status abnormal alarm."
		::=  {  trap-30864-reasoninfo 1}

-- 1.3.6.1.4.1.3902.6053.19.1.3.11.1.30864.2
    trapFanSpeedStatusAbnormalByMaintenanceAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Fan speed status abnormal alarm."
		::=  {  trap-30864-reasoninfo 2}
		
-- 1.3.6.1.4.1.3902.6053.19.1.3.11.1.30865
    trap-30865-addinfo OBJECT IDENTIFIER ::= {trap-addinfo 30865}
	
-- 1.3.6.1.4.1.3902.6053.19.1.3.11.1.30865
    trapMemoryCriticalOvertemperatureAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"The memory in this area is critical overtemperature."
		::=  {  trap-alarm 30865}

-- 1.3.6.1.4.1.3902.6053.19.1.3.11.1.30865
    trap-30865-reasoninfo OBJECT IDENTIFIER ::= {trap-alarm 30865}

-- 1.3.6.1.4.1.3902.6053.19.1.3.11.1.30865.1
    trapCPUMemoryCriticalOvertemperatureAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"The memory in this area is critical overtemperature."
		::=  {  trap-30865-reasoninfo 1}
		
-- 1.3.6.1.4.1.3902.6053.19.1.3.11.1.30866
    trap-30866-addinfo OBJECT IDENTIFIER ::= {trap-addinfo 30866}
	
-- 1.3.6.1.4.1.3902.6053.19.1.3.11.1.30866
    trapSystemFirmwareAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"System firmware status abnormal alarm."
		::=  {  trap-alarm 30866}

-- 1.3.6.1.4.1.3902.6053.19.1.3.11.1.30866
    trap-30866-reasoninfo OBJECT IDENTIFIER ::= {trap-alarm 30866}

-- 1.3.6.1.4.1.3902.6053.19.1.3.11.1.30866.1
    trapSystemFirmwareNotHaveMemoryAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"System firmware status abnormal alarm."
		::=  {  trap-30866-reasoninfo 1}		

-- 1.3.6.1.4.1.3902.6053.19.1.3.11.1.30866.2
    trapSystemFirmwareIsolatedMemoryAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"System firmware status abnormal alarm."
		::=  {  trap-30866-reasoninfo 2}
		
-- 1.3.6.1.4.1.3902.6053.19.1.3.11.1.30867
    trap-30867-addinfo OBJECT IDENTIFIER ::= {trap-addinfo 30867}
	
-- 1.3.6.1.4.1.3902.6053.19.1.3.11.1.30867
    trapPowerFaultAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Abnormal power on alarm."
		::=  {  trap-alarm 30867}

-- 1.3.6.1.4.1.3902.6053.19.1.3.11.1.30867
    trap-30867-reasoninfo OBJECT IDENTIFIER ::= {trap-alarm 30867}

-- 1.3.6.1.4.1.3902.6053.19.1.3.11.1.30867.1
    trapCPUPowerFaultAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Abnormal power on alarm."
		::=  {  trap-30867-reasoninfo 1}

-- 1.3.6.1.4.1.3902.6053.19.1.3.11.1.30867.2
    trapDIMMPowerFaultAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Abnormal power on alarm."
		::=  {  trap-30867-reasoninfo 2}  
		
-- 1.3.6.1.4.1.3902.6053.19.1.3.11.1.30867.3
    trapOtherPowerFaultAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Abnormal power on alarm."
		::=  {  trap-30867-reasoninfo 3}
		
-- 1.3.6.1.4.1.3902.6053.19.1.3.11.1.30870
    trap-30870-addinfo OBJECT IDENTIFIER ::= {trap-addinfo 30870}

-- 1.3.6.1.4.1.3902.6053.19.1.3.11.2.30870.1
    trap-30870-ucPortId OBJECT-TYPE
        SYNTAX Unsigned32
        ACCESS accessible-for-notify
        STATUS current
        DESCRIPTION 
            "Port ID"
        ::= {trap-30870-addinfo 1}

-- 1.3.6.1.4.1.3902.6053.19.1.3.11.2.30870.2
    trap-30870-cLocation OBJECT-TYPE
        SYNTAX DisplayString
        ACCESS accessible-for-notify
        STATUS current
        DESCRIPTION 
            "Location"
        ::= {trap-30870-addinfo 2}

-- 1.3.6.1.4.1.3902.6053.19.1.3.11.1.30870
    trapOpticalModuleStatusAbnormalAlarm  	NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30870-ucPortId, trap-30870-cLocation, acTrapTime, acTrapEventSubject, acTrapSeverity, acTrapDescription, acTrapProductSerial, acTrapState, acTrapDeviceSN, acTrapAddInform, dwTrapIndex
                                                }
        STATUS          current
        DESCRIPTION     "Optical module status abnormal alarm."
        ::=  {  trap-alarm 30870}

-- 1.3.6.1.4.1.3902.6053.19.1.3.11.1.30870
    trap-30870-reasoninfo OBJECT IDENTIFIER ::= {trap-alarm 30870}
 
-- 1.3.6.1.4.1.3902.6053.19.1.3.11.1.30870.1
    trapEmbeddedOpticalModuleStatusAbnormalAlarm  	NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30870-ucPortId, trap-30870-cLocation, acTrapTime, acTrapEventSubject, acTrapSeverity, acTrapDescription, acTrapProductSerial, acTrapState, acTrapDeviceSN, acTrapAddInform, dwTrapIndex
                                                }
        STATUS          current
        DESCRIPTION     "Optical module status abnormal alarm."
        ::=  {  trap-30870-reasoninfo 1}

-- 1.3.6.1.4.1.3902.6053.19.1.3.11.1.30870.2
    trapOcpOpticalModuleStatusAbnormalAlarm  	NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30870-ucPortId, trap-30870-cLocation, acTrapTime, acTrapEventSubject, acTrapSeverity, acTrapDescription, acTrapProductSerial, acTrapState, acTrapDeviceSN, acTrapAddInform, dwTrapIndex
                                                }
        STATUS          current
        DESCRIPTION     "Optical module status abnormal alarm."
        ::=  {  trap-30870-reasoninfo 2}
        
-- 1.3.6.1.4.1.3902.6053.19.1.3.11.1.30870.3
    trapCommOpticalModuleStatusAbnormalAlarm  	NOTIFICATION-TYPE
        OBJECTS         {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30870-ucPortId, trap-30870-cLocation, acTrapTime, acTrapEventSubject, acTrapSeverity, acTrapDescription, acTrapProductSerial, acTrapState, acTrapDeviceSN, acTrapAddInform, dwTrapIndex
                                                }
        STATUS          current
        DESCRIPTION     "Optical module status abnormal alarm."
        ::=  {  trap-30870-reasoninfo 3} 

-- 1.3.6.1.4.1.3902.6053.19.1.3.11.1.30880
    trapPSUOutputStatusAbnormalAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Abnormal PSU Output."
		::=  {  trap-alarm 30880}

-- 1.3.6.1.4.1.3902.6053.19.1.3.11.1.30880
    trap-30880-reasoninfo OBJECT IDENTIFIER ::= {trap-alarm 30880}

-- 1.3.6.1.4.1.3902.6053.19.1.3.11.1.30880.1
    trapPSUOutputStatusPowerOKAbnormalAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Abnormal PSU Output."
		::=  {  trap-30880-reasoninfo 1}

-- 1.3.6.1.4.1.3902.6053.19.1.3.11.1.30881
    trapPSUFANStatusAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Predictive failure alarm."
		::=  {  trap-alarm 30881}

-- 1.3.6.1.4.1.3902.6053.19.1.3.11.1.30881
    trap-30881-reasoninfo OBJECT IDENTIFIER ::= {trap-alarm 30881}

-- 1.3.6.1.4.1.3902.6053.19.1.3.11.1.30881.1
    trapPSUFANStatusPredictiveFailureAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Predictive failure alarm."
		::=  {  trap-30881-reasoninfo 1}
-- 1.3.6.1.4.1.3902.6053.19.1.3.11.1.30890
    trap-30890-addinfo OBJECT IDENTIFIER ::= {trap-addinfo 30890}

-- 1.3.6.1.4.1.3902.6053.19.1.3.11.2.30890.2
    trap-30890-ucMemoryLocation OBJECT-TYPE
        SYNTAX Unsigned32
        ACCESS accessible-for-notify
        STATUS current
        DESCRIPTION 
            "Memory location"
        ::= {trap-30890-addinfo 2}

-- 1.3.6.1.4.1.3902.6053.19.1.3.11.2.30890.3
    trap-30890-ucSlotId OBJECT-TYPE
        SYNTAX Unsigned32
        {
            na(255)
        }
        ACCESS accessible-for-notify
        STATUS current
        DESCRIPTION 
            "Memory Riser Index"
        ::= {trap-30890-addinfo 3}

-- 1.3.6.1.4.1.3902.6053.19.1.3.11.1.30890
    trapCorrectableMemoryErrorMinorInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30890-ucMemoryLocation, trap-30890-ucSlotId, acTrapTime, acTrapEventSubject, acTrapSeverity, acTrapDescription, acTrapProductSerial, acTrapState, acTrapDeviceSN, acTrapAddInform, dwTrapIndex
		                                        }
		STATUS			current
		DESCRIPTION		"correctable ECC error minor alarm limit reached."
		::=  {  trap-alarm 30890}

-- 1.3.6.1.4.1.3902.6053.19.1.3.11.1.30890
    trap-30890-reasoninfo OBJECT IDENTIFIER ::= {trap-alarm 30890}

-- 1.3.6.1.4.1.3902.6053.19.1.3.11.1.30890.1
    trapCorrectableMemoryErrorMinorLimitReachedInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30890-ucMemoryLocation, trap-30890-ucSlotId, acTrapTime, acTrapEventSubject, acTrapSeverity, acTrapDescription, acTrapProductSerial, acTrapState, acTrapDeviceSN, acTrapAddInform, dwTrapIndex
		                                        }
		STATUS			current
		DESCRIPTION		"correctable ECC error minor alarm limit reached."
		::=  {  trap-30890-reasoninfo 1}

-- 1.3.6.1.4.1.3902.6053.19.1.3.11.1.30891
    trap-30891-addinfo OBJECT IDENTIFIER ::= {trap-addinfo 30891}

-- 1.3.6.1.4.1.3902.6053.19.1.3.11.2.30891.2
    trap-30891-ucMemoryLocation OBJECT-TYPE
        SYNTAX Unsigned32
        ACCESS accessible-for-notify
        STATUS current
        DESCRIPTION 
            "Memory location"
        ::= {trap-30891-addinfo 2}

-- 1.3.6.1.4.1.3902.6053.19.1.3.11.2.30891.3
    trap-30891-ucSlotId OBJECT-TYPE
        SYNTAX Unsigned32
        {
            na(255)
        }
        ACCESS accessible-for-notify
        STATUS current
        DESCRIPTION 
            "Memory Riser Index"
        ::= {trap-30891-addinfo 3}

-- 1.3.6.1.4.1.3902.6053.19.1.3.11.1.30891
    trapCorrectableMemoryErrorMinorAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30891-ucMemoryLocation, trap-30891-ucSlotId, acTrapTime, acTrapEventSubject, acTrapSeverity, acTrapDescription, acTrapProductSerial, acTrapState, acTrapDeviceSN, acTrapAddInform, dwTrapIndex
		                                        }
		STATUS			current
		DESCRIPTION		"correctable ECC error minor alarm limit reached."
		::=  {  trap-alarm 30891}

-- 1.3.6.1.4.1.3902.6053.19.1.3.11.1.30891
    trap-30891-reasoninfo OBJECT IDENTIFIER ::= {trap-alarm 30891}

-- 1.3.6.1.4.1.3902.6053.19.1.3.11.1.30891.1
    trapCorrectableMemoryErrorMinorLimitReachedAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30891-ucMemoryLocation, trap-30891-ucSlotId, acTrapTime, acTrapEventSubject, acTrapSeverity, acTrapDescription, acTrapProductSerial, acTrapState, acTrapDeviceSN, acTrapAddInform, dwTrapIndex
		                                        }
		STATUS			current
		DESCRIPTION		"correctable ECC error minor alarm limit reached."
		::=  {  trap-30891-reasoninfo 1}

-- 1.3.6.1.4.1.3902.6053.19.1.3.11.1.30900
    trap-30900-addinfo OBJECT IDENTIFIER ::= {trap-addinfo 30900}

-- 1.3.6.1.4.1.3902.6053.19.1.3.11.2.30900.1
    trap-30900-slot OBJECT-TYPE
        SYNTAX Unsigned32
        ACCESS accessible-for-notify
        STATUS current
        DESCRIPTION 
            "Slot"
        ::= {trap-30900-addinfo 1}
-- 1.3.6.1.4.1.3902.6053.19.1.3.11.1.30900
    trapSmartNicDetectStart 	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30850-ucStatus,trap-30850-aucSensorName, acTrapTime, acTrapEventSubject, acTrapSeverity, acTrapDescription, acTrapProductSerial, acTrapState, acTrapDeviceSN, acTrapAddInform, dwTrapIndex
		                                        }
		STATUS			current
		DESCRIPTION		"Wating Taihang Post Start."
		::=  {  trap-alarm 30900}

-- 1.3.6.1.4.1.3902.6053.19.1.3.11.1.30900
    trap-30900-reasoninfo OBJECT IDENTIFIER ::= {trap-alarm 30900}

-- 1.3.6.1.4.1.3902.6053.19.1.3.11.1.30900.1
    trapSmartNicDetectPostStart 	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30850-ucStatus,trap-30850-aucSensorName, acTrapTime, acTrapEventSubject, acTrapSeverity, acTrapDescription, acTrapProductSerial, acTrapState, acTrapDeviceSN, acTrapAddInform, dwTrapIndex
		                                        }
		STATUS			current
		DESCRIPTION		"Wating Taihang Post Start."
		::=  {  trap-30900-reasoninfo 1}

-- 1.3.6.1.4.1.3902.6053.19.1.3.11.1.30901
    trap-30901-addinfo OBJECT IDENTIFIER ::= {trap-addinfo 30901}

-- 1.3.6.1.4.1.3902.6053.19.1.3.11.2.30901.1
    trap-30901-slot OBJECT-TYPE
        SYNTAX Unsigned32
        ACCESS accessible-for-notify
        STATUS current
        DESCRIPTION 
            "Slot"
        ::= {trap-30901-addinfo 1}
-- 1.3.6.1.4.1.3902.6053.19.1.3.11.1.30901
    trapSmartNicDetectSuccess  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30850-ucStatus,trap-30850-aucSensorName, acTrapTime, acTrapEventSubject, acTrapSeverity, acTrapDescription, acTrapProductSerial, acTrapState, acTrapDeviceSN, acTrapAddInform, dwTrapIndex
		                                        }
		STATUS			current
		DESCRIPTION		"Wating Taihang Post Success."
		::=  {  trap-alarm 30901}

-- 1.3.6.1.4.1.3902.6053.19.1.3.11.1.30901
    trap-30901-reasoninfo OBJECT IDENTIFIER ::= {trap-alarm 30901}   
    
-- 1.3.6.1.4.1.3902.6053.19.1.3.11.1.30901.1
    trapSmartNicDetectPostSuccess  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30850-ucStatus,trap-30850-aucSensorName, acTrapTime, acTrapEventSubject, acTrapSeverity, acTrapDescription, acTrapProductSerial, acTrapState, acTrapDeviceSN, acTrapAddInform, dwTrapIndex
		                                        }
		STATUS			current
		DESCRIPTION		"Wating Taihang Post Success."
		::=  {  trap-30901-reasoninfo 1}
	
-- 1.3.6.1.4.1.3902.6053.19.1.3.11.1.30902
    trap-30902-addinfo OBJECT IDENTIFIER ::= {trap-addinfo 30902}
	
-- 1.3.6.1.4.1.3902.6053.19.1.3.11.1.30902.1
    trap-30902-slot OBJECT-TYPE
        SYNTAX Unsigned32
        ACCESS accessible-for-notify
        STATUS current
        DESCRIPTION 
            "Slot"
        ::= {trap-30902-addinfo 1}

-- 1.3.6.1.4.1.3902.6053.19.1.3.11.1.30902
    trapSmartNicDetectSocError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"SOC Post failed."
		::=  {  trap-alarm 30902}

-- 1.3.6.1.4.1.3902.6053.19.1.3.11.1.30902
    trap-30902-reasoninfo OBJECT IDENTIFIER ::= {trap-alarm 30902} 

-- 1.3.6.1.4.1.3902.6053.19.1.3.11.1.30902.1
    trapCommSmartNicDetectSocError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"SOC Post failed."
		::=  {  trap-30902-reasoninfo 1}

-- 1.3.6.1.4.1.3902.6053.19.1.3.11.1.30902.2
    trapBF2SmartNicDetectSocError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"SOC Post failed."
		::=  {  trap-30902-reasoninfo 2}

-- 1.3.6.1.4.1.3902.6053.19.1.3.11.1.30902.3
    trapZiJinSmartNicDetectSocError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"SOC Post failed."
		::=  {  trap-30902-reasoninfo 3}

-- 1.3.6.1.4.1.3902.6053.19.1.3.11.1.30903
    trap-30903-addinfo OBJECT IDENTIFIER ::= {trap-addinfo 30903}
-- 1.3.6.1.4.1.3902.6053.19.1.3.11.1.30903.1
    trap-30903-slot OBJECT-TYPE
        SYNTAX Unsigned32
        ACCESS accessible-for-notify
        STATUS current
        DESCRIPTION 
            "Slot"
        ::= {trap-30903-addinfo 1}

-- 1.3.6.1.4.1.3902.6053.19.1.3.11.1.30903
    trapSmartNicDetectBiosError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"BIOS Post failed."
		::=  {  trap-alarm 30903} 
		
-- 1.3.6.1.4.1.3902.6053.19.1.3.11.1.30903
    trap-30903-reasoninfo OBJECT IDENTIFIER ::= {trap-alarm 30903} 		

-- 1.3.6.1.4.1.3902.6053.19.1.3.11.1.30903.1
    trapSmartNicDetectBiosErrorAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"BIOS Post failed."
		::=  {  trap-30903-reasoninfo 1} 		
		
-- 1.3.6.1.4.1.3902.6053.19.1.3.11.1.30905
    trap-30905-addinfo OBJECT IDENTIFIER ::= { trap-addinfo 30905 }

-- 1.3.6.1.4.1.3902.6053.19.1.3.11.1.30905.1
    trap-30905-componentSN OBJECT-TYPE
        SYNTAX DisplayString
        ACCESS accessible-for-notify
        STATUS current
        DESCRIPTION
            "component SN."
        ::= { trap-30905-addinfo 1 }

-- 1.3.6.1.4.1.3902.6053.19.1.3.11.1.30905.2
    trap-30905-componentModel OBJECT-TYPE
        SYNTAX DisplayString
        ACCESS accessible-for-notify
        STATUS current
        DESCRIPTION
            "component model."
        ::= { trap-30905-addinfo 2 }

-- 1.3.6.1.4.1.3902.6053.19.1.3.11.1.30905.3
    trap-30905-assetChangeType OBJECT-TYPE
        SYNTAX Unsigned32
        {
            component-add(1),
            component-change(2),
            component-delete(3)
        }
        ACCESS accessible-for-notify
        STATUS current
        DESCRIPTION
            "asset change type."
        ::= { trap-30905-addinfo 3 }

-- 1.3.6.1.4.1.3902.6053.19.1.3.11.1.30905.4
    trap-30905-silkName OBJECT-TYPE
        SYNTAX DisplayString
        ACCESS accessible-for-notify
        STATUS current
        DESCRIPTION
            "silk name."
        ::= { trap-30905-addinfo 4 }

-- 1.3.6.1.4.1.3902.6053.19.1.3.11.1.30905
    trapAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-alarm 30905 }
 
-- 1.3.6.1.4.1.3902.6053.19.1.3.11.1.30905
    trap-30905-reasoninfo OBJECT IDENTIFIER ::= {trap-alarm 30905}

-- 1.3.6.1.4.1.3902.6053.19.1.3.11.1.30905.1
    trapMemoryAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 1 }

-- 1.3.6.1.4.1.3902.6053.19.1.3.11.1.30905.2
    trapCpuAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 2 }

-- 1.3.6.1.4.1.3902.6053.19.1.3.11.1.30905.3
    trapDiskAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 3 }

-- 1.3.6.1.4.1.3902.6053.19.1.3.11.1.30905.4
    trapMainBoardAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 4 }

-- 1.3.6.1.4.1.3902.6053.19.1.3.11.1.30905.5
    trapPowerAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 5 }

-- 1.3.6.1.4.1.3902.6053.19.1.3.11.1.30905.6
    trapRaidAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 6 }

-- 1.3.6.1.4.1.3902.6053.19.1.3.11.1.30905.7
    trapNetcardOnBoardAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 7 }

-- 1.3.6.1.4.1.3902.6053.19.1.3.11.1.30905.8
    trapNetcardOnPcieAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 8 }

-- 1.3.6.1.4.1.3902.6053.19.1.3.11.1.30905.9
    trapNetcardOnOcpAssetChanged NOTIFICATION-TYPE
        OBJECTS         {dwAlarmID, tAlarmTime, ucAlarmFlag, ucRestoreType, ucAlarmSeverity, dwDeviceType, dwDeviceID, dwCrcCode1, dwCrcCode2, dwCrcCode3, acAlarmDesc, tAlarmUTCTime, trap-30905-componentSN, trap-30905-componentModel, trap-30905-assetChangeType, trap-30905-silkName, acTrapTime, acTrapEventSubject, acTrapSeverity, acTrapDescription, acTrapProductSerial, acTrapState, acTrapDeviceSN, acTrapAddInform, dwTrapIndex}
        STATUS          current
        DESCRIPTION     "Asset Change Notification."
        ::= { trap-30905-reasoninfo 9 } 
 
-- 1.3.6.1.4.1.3902.6053.19.1.3.11.1.30907
    trap-30907-addinfo OBJECT IDENTIFIER ::= {trap-addinfo 30907}

-- 1.3.6.1.4.1.3902.6053.19.1.3.11.1.30907
    trapCpuMceInform        NOTIFICATION-TYPE
                OBJECTS                 {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30907-ucCpuErrType, acTrapTime, acTrapEventSubject, acTrapSeverity, acTrapDescription, acTrapProductSerial, acTrapState, acTrapDeviceSN, acTrapAddInform, dwTrapIndex
                                                        }
                STATUS                  current
                DESCRIPTION             "a Machine Check Exception occured recently."
                ::=  {  trap-alarm 30907}

-- 1.3.6.1.4.1.3902.6053.19.1.3.11.1.30907
    trap-30907-reasoninfo OBJECT IDENTIFIER ::= {trap-alarm 30907}

-- 1.3.6.1.4.1.3902.6053.19.1.3.11.1.30907.1
    trapCpuMceOccuredRecentlyInform        NOTIFICATION-TYPE
                OBJECTS                 {  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30907-ucCpuErrType, acTrapTime, acTrapEventSubject, acTrapSeverity, acTrapDescription, acTrapProductSerial, acTrapState, acTrapDeviceSN, acTrapAddInform, dwTrapIndex
                                                        }
                STATUS                  current
                DESCRIPTION             "a Machine Check Exception occured recently."
                ::=  {  trap-30907-reasoninfo 1}

-- 1.3.6.1.4.1.3902.6053.19.1.3.11.1.30911
    trap-30911-addinfo OBJECT IDENTIFIER ::= {trap-addinfo 30911}

-- 1.3.6.1.4.1.3902.6053.19.1.3.11.2.30911.1
    trap-30911-ucIdeLocation OBJECT-TYPE
        SYNTAX Unsigned32
        ACCESS accessible-for-notify
        STATUS current
        DESCRIPTION 
            "Nvme location"
        ::= {trap-30911-addinfo 1}
		
-- 1.3.6.1.4.1.3902.6053.19.1.3.11.2.30911.2
    trap-30911-ucZone OBJECT-TYPE
        SYNTAX Unsigned32
        ACCESS accessible-for-notify
        STATUS current
        DESCRIPTION 
            "Nvme zone"
        ::= {trap-30911-addinfo 2}

-- 1.3.6.1.4.1.3902.6053.19.1.3.11.2.30911.3
    trap-30911-ucType OBJECT-TYPE
        SYNTAX Unsigned32
        {
            nvme(0),
            aic(1)
        }
        ACCESS accessible-for-notify
        STATUS current
        DESCRIPTION 
            "Nvme Type"
        ::= {trap-30911-addinfo 3}

-- 1.3.6.1.4.1.3902.6053.19.1.3.11.1.30911
    trapNVMEAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30911-ucIdeLocation,trap-30911-ucZone, acTrapTime, acTrapEventSubject, acTrapSeverity, acTrapDescription, acTrapProductSerial, acTrapState, acTrapDeviceSN, acTrapAddInform, dwTrapIndex
		                                        }
		STATUS			current
		DESCRIPTION		"Nvme link is abnormal"
		::=  {  trap-alarm 30911}
		
-- 1.3.6.1.4.1.3902.6053.19.1.3.11.1.30911
    trap-30911-reasoninfo OBJECT IDENTIFIER ::= {trap-alarm 30911}

-- 1.3.6.1.4.1.3902.6053.19.1.3.11.1.30911.1
    trapCommNVMEAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30911-ucIdeLocation,trap-30911-ucZone, acTrapTime, acTrapEventSubject, acTrapSeverity, acTrapDescription, acTrapProductSerial, acTrapState, acTrapDeviceSN, acTrapAddInform, dwTrapIndex
		                                        }
		STATUS			current
		DESCRIPTION		"Nvme link is abnormal"
		::=  {  trap-30911-reasoninfo 1}

-- 1.3.6.1.4.1.3902.6053.19.1.3.11.1.30911.2
    trapFrontNVMEAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30911-ucIdeLocation,trap-30911-ucZone, acTrapTime, acTrapEventSubject, acTrapSeverity, acTrapDescription, acTrapProductSerial, acTrapState, acTrapDeviceSN, acTrapAddInform, dwTrapIndex
		                                        }
		STATUS			current
		DESCRIPTION		"Nvme link is abnormal"
		::=  {  trap-30911-reasoninfo 2}

-- 1.3.6.1.4.1.3902.6053.19.1.3.11.1.30911.3
    trapRearNVMEAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30911-ucIdeLocation,trap-30911-ucZone, acTrapTime, acTrapEventSubject, acTrapSeverity, acTrapDescription, acTrapProductSerial, acTrapState, acTrapDeviceSN, acTrapAddInform, dwTrapIndex
		                                        }
		STATUS			current
		DESCRIPTION		"Nvme link is abnormal"
		::=  {  trap-30911-reasoninfo 3}

-- 1.3.6.1.4.1.3902.6053.19.1.3.11.1.30911.4
    trapOsNVMEAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30911-ucIdeLocation,trap-30911-ucZone, acTrapTime, acTrapEventSubject, acTrapSeverity, acTrapDescription, acTrapProductSerial, acTrapState, acTrapDeviceSN, acTrapAddInform, dwTrapIndex
		                                        }
		STATUS			current
		DESCRIPTION		"Nvme link is abnormal"
		::=  {  trap-30911-reasoninfo 4}

-- 1.3.6.1.4.1.3902.6053.19.1.3.11.1.30911.5
    trapAICNVMEAbnormal  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30911-ucIdeLocation,trap-30911-ucZone, acTrapTime, acTrapEventSubject, acTrapSeverity, acTrapDescription, acTrapProductSerial, acTrapState, acTrapDeviceSN, acTrapAddInform, dwTrapIndex
		                                        }
		STATUS			current
		DESCRIPTION		"Nvme link is abnormal"
		::=  {  trap-30911-reasoninfo 5}		
		
-- 1.3.6.1.4.1.3902.6053.19.1.3.11.1.30912
    trap-30912-addinfo OBJECT IDENTIFIER ::= {trap-addinfo 30912}

-- 1.3.6.1.4.1.3902.6053.19.1.3.11.2.30912.1
    trap-30912-ucIdeLocation OBJECT-TYPE
        SYNTAX Unsigned32
        ACCESS accessible-for-notify
        STATUS current
        DESCRIPTION 
            "Nvme location"
        ::= {trap-30912-addinfo 1}
		
-- 1.3.6.1.4.1.3902.6053.19.1.3.11.2.30912.2
    trap-30912-ucZone OBJECT-TYPE
        SYNTAX Unsigned32
        ACCESS accessible-for-notify
        STATUS current
        DESCRIPTION 
            "Nvme zone"
        ::= {trap-30912-addinfo 2}

-- 1.3.6.1.4.1.3902.6053.19.1.3.11.2.30912.3
    trap-30912-ucType OBJECT-TYPE
        SYNTAX Unsigned32
        {
            nvme(0),
            aic(1)
        }
        ACCESS accessible-for-notify
        STATUS current
        DESCRIPTION 
            "Nvme Type"
        ::= {trap-30912-addinfo 3}

-- 1.3.6.1.4.1.3902.6053.19.1.3.11.1.30912
    trapNVMEFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30912-ucIdeLocation,trap-30912-ucZone, acTrapTime, acTrapEventSubject, acTrapSeverity, acTrapDescription, acTrapProductSerial, acTrapState, acTrapDeviceSN, acTrapAddInform, dwTrapIndex
		                                        }
		STATUS			current
		DESCRIPTION		"Nvme has failure."
		::=  {  trap-alarm 30912}

-- 1.3.6.1.4.1.3902.6053.19.1.3.11.1.30912
    trap-30912-reasoninfo OBJECT IDENTIFIER ::= {trap-alarm 30912}

-- 1.3.6.1.4.1.3902.6053.19.1.3.11.1.30912.1
    trapCommNVMEFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30912-ucIdeLocation,trap-30912-ucZone, acTrapTime, acTrapEventSubject, acTrapSeverity, acTrapDescription, acTrapProductSerial, acTrapState, acTrapDeviceSN, acTrapAddInform, dwTrapIndex
		                                        }
		STATUS			current
		DESCRIPTION		"Nvme has failure."
		::=  {  trap-30912-reasoninfo 1}

-- 1.3.6.1.4.1.3902.6053.19.1.3.11.1.30912.2
    trapFrontNVMEFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30912-ucIdeLocation,trap-30912-ucZone, acTrapTime, acTrapEventSubject, acTrapSeverity, acTrapDescription, acTrapProductSerial, acTrapState, acTrapDeviceSN, acTrapAddInform, dwTrapIndex
		                                        }
		STATUS			current
		DESCRIPTION		"Nvme has failure."
		::=  {  trap-30912-reasoninfo 2}  
		
-- 1.3.6.1.4.1.3902.6053.19.1.3.11.1.30912.3
    trapRearNVMEFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30912-ucIdeLocation,trap-30912-ucZone, acTrapTime, acTrapEventSubject, acTrapSeverity, acTrapDescription, acTrapProductSerial, acTrapState, acTrapDeviceSN, acTrapAddInform, dwTrapIndex
		                                        }
		STATUS			current
		DESCRIPTION		"Nvme has failure."
		::=  {  trap-30912-reasoninfo 3} 
		
-- 1.3.6.1.4.1.3902.6053.19.1.3.11.1.30912.4
    trapOsNVMEFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30912-ucIdeLocation,trap-30912-ucZone, acTrapTime, acTrapEventSubject, acTrapSeverity, acTrapDescription, acTrapProductSerial, acTrapState, acTrapDeviceSN, acTrapAddInform, dwTrapIndex
		                                        }
		STATUS			current
		DESCRIPTION		"Nvme has failure."
		::=  {  trap-30912-reasoninfo 4}

-- 1.3.6.1.4.1.3902.6053.19.1.3.11.1.30912.5
    trapAICNVMEFailure  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30912-ucIdeLocation,trap-30912-ucZone, acTrapTime, acTrapEventSubject, acTrapSeverity, acTrapDescription, acTrapProductSerial, acTrapState, acTrapDeviceSN, acTrapAddInform, dwTrapIndex
		                                        }
		STATUS			current
		DESCRIPTION		"Nvme has failure."
		::=  {  trap-30912-reasoninfo 5}

-- 1.3.6.1.4.1.3902.6053.19.1.3.11.1.30913
    trap-30913-addinfo OBJECT IDENTIFIER ::= {trap-addinfo 30913}

-- 1.3.6.1.4.1.3902.6053.19.1.3.11.1.30913
    liquidSystemLeakageAbsent  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Liquid cooling system but the Liquid-card is not present."
		::=  {  trap-alarm 30913}
		
-- 1.3.6.1.4.1.3902.6053.19.1.3.11.1.30913
    trap-30913-reasoninfo OBJECT IDENTIFIER ::= {trap-alarm 30913}		

-- 1.3.6.1.4.1.3902.6053.19.1.3.11.1.30913.1
    liquidSystemLeakageAbsentAlarm  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"Liquid cooling system but the Liquid-card is not present."
		::=  {  trap-30913-reasoninfo 1}		
			
-- 1.3.6.1.4.1.3902.6053.19.1.3.11.1.30916
    trap-30916-addinfo OBJECT IDENTIFIER ::= {trap-addinfo 30916}

-- 1.3.6.1.4.1.3902.6053.19.1.3.11.1.30916
    trapCpuConfigureError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"CPU configure error."
		::=  {  trap-alarm 30916} 
		
-- 1.3.6.1.4.1.3902.6053.19.1.3.11.1.30916
    trap-30916-reasoninfo OBJECT IDENTIFIER ::= {trap-alarm 30916}
		
-- 1.3.6.1.4.1.3902.6053.19.1.3.11.1.30916.1
    trapCpuConfigureBiosVersionMismatchError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"CPU configure error."
		::=  {  trap-30916-reasoninfo 1}

-- 1.3.6.1.4.1.3902.6053.19.1.3.11.1.30916.2
    trapCpuConfigureCommError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, acTrapTime, acTrapEventSubject, acTrapSeverity, acTrapDescription, acTrapProductSerial, acTrapState, acTrapDeviceSN, acTrapAddInform, dwTrapIndex
		                                        }
		STATUS			current
		DESCRIPTION		"CPU configure error."
		::=  {  trap-30916-reasoninfo 2}		
		
-- 1.3.6.1.4.1.3902.6053.19.1.3.11.1.30919
    trap-30919-addinfo OBJECT IDENTIFIER ::= {trap-addinfo 30919}

-- 1.3.6.1.4.1.3902.6053.19.1.3.11.2.30919.1
    trap-30919-ucDevType OBJECT-TYPE
        SYNTAX Unsigned32
        ACCESS accessible-for-notify
        STATUS current
        DESCRIPTION 
            "PCIE Device Type"
        ::= {trap-30919-addinfo 1}

-- 1.3.6.1.4.1.3902.6053.19.1.3.11.2.30919.2
    trap-30919-ucDevIndex OBJECT-TYPE
        SYNTAX Unsigned32
        ACCESS accessible-for-notify
        STATUS current
        DESCRIPTION 
            "Solt No"
        ::= {trap-30919-addinfo 2}
        
-- 1.3.6.1.4.1.3902.6053.19.1.3.11.1.30919
    trapEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30919-ucDevType, trap-30919-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-alarm 30919} 

-- 1.3.6.1.4.1.3902.6053.19.1.3.11.1.30919
    trap-30919-reasoninfo OBJECT IDENTIFIER ::= {trap-alarm 30919}

-- 1.3.6.1.4.1.3902.6053.19.1.3.11.1.30919.1
    trapOnboardDiskControllerEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30919-ucDevType, trap-30919-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 1}

-- 1.3.6.1.4.1.3902.6053.19.1.3.11.1.30919.2
    trapOnboardNetcardEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30919-ucDevType, trap-30919-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 2}

-- 1.3.6.1.4.1.3902.6053.19.1.3.11.1.30919.3
    trapOnboardVGAEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 3}

-- 1.3.6.1.4.1.3902.6053.19.1.3.11.1.30919.4
    trapOnboardPCIeSwitchEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 4}

-- 1.3.6.1.4.1.3902.6053.19.1.3.11.1.30919.5
    trapRTMEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 5}

-- 1.3.6.1.4.1.3902.6053.19.1.3.11.1.30919.6
    trapM2EDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 6}

-- 1.3.6.1.4.1.3902.6053.19.1.3.11.1.30919.7
    trapBackplaneEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 7}

-- 1.3.6.1.4.1.3902.6053.19.1.3.11.1.30919.8
    trapExpcardEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 8}

-- 1.3.6.1.4.1.3902.6053.19.1.3.11.1.30919.9
    trapOCPCardEDPCEventInform 	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 9}

-- 1.3.6.1.4.1.3902.6053.19.1.3.11.1.30919.10
    trapPCIESlotEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 10}

-- 1.3.6.1.4.1.3902.6053.19.1.3.11.1.30919.11
    trapNvmeCardEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 11}

-- 1.3.6.1.4.1.3902.6053.19.1.3.11.1.30919.12
    trapRaidCardEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 12}

-- 1.3.6.1.4.1.3902.6053.19.1.3.11.1.30919.13
    trapNetCardEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 13}

-- 1.3.6.1.4.1.3902.6053.19.1.3.11.1.30919.14
    trapSlotEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 14}

-- 1.3.6.1.4.1.3902.6053.19.1.3.11.1.30919.15
    trapSASCardEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 15}

-- 1.3.6.1.4.1.3902.6053.19.1.3.11.1.30919.16
    trapSMBUSPCIESlotEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 16}

-- 1.3.6.1.4.1.3902.6053.19.1.3.11.1.30919.17
    trapUnKnownEDPCEventInform  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30834-ucDevType, trap-30834-ucDevIndex, acTrapTime, acTrapEventSubject, acTrapSeverity, acTrapDescription, acTrapProductSerial, acTrapState, acTrapDeviceSN, acTrapAddInform, dwTrapIndex 
		                                        }
		STATUS			current
		DESCRIPTION		"PCIE edpc event."
		::=  {  trap-30919-reasoninfo 17}

-- 1.3.6.1.4.1.3902.6053.19.1.3.11.1.30920
    trap-30920-addinfo OBJECT IDENTIFIER ::= {trap-addinfo 30920}

-- 1.3.6.1.4.1.3902.6053.19.1.3.11.2.30920.1
    trap-30920-ucCpuId OBJECT-TYPE
        SYNTAX Unsigned32
        ACCESS accessible-for-notify
        STATUS current
        DESCRIPTION 
            "CPU number"
        ::= {trap-30920-addinfo 1}

-- 1.3.6.1.4.1.3902.6053.19.1.3.11.1.30920
    trapFRB1BISTError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30781-ucCpuId, acTrapTime, acTrapEventSubject, acTrapSeverity, acTrapDescription, acTrapProductSerial, acTrapState, acTrapDeviceSN, acTrapAddInform, dwTrapIndex
		                                        }
		STATUS			current
		DESCRIPTION		"FRB1/BIST Failure."
		::=  {  trap-alarm 30920}

-- 1.3.6.1.4.1.3902.6053.19.1.3.11.1.30920
    trap-30920-reasoninfo OBJECT IDENTIFIER ::= {trap-alarm 30920}

-- 1.3.6.1.4.1.3902.6053.19.1.3.11.1.30920.1
    trapCPUFRB1BISTError  	NOTIFICATION-TYPE
		OBJECTS			{  dwAlarmID, tAlarmTime, ucAlarmFlag, ucRestoreType, ucAlarmSeverity, dwDeviceType, dwDeviceID, ucSubSystem, wModule, wUnit, ucSUnit, dwCrcCode1, dwCrcCode2, dwCrcCode3, dwCrcCode4, wNtlvLen, wAlarmObj, wObjLen, acAlarmDesc, tAlarmUTCTime, trap-30920-ucCpuId, acTrapTime, acTrapEventSubject, acTrapSeverity, acTrapDescription, acTrapProductSerial, acTrapState, acTrapDeviceSN, acTrapAddInform, dwTrapIndex
		                                        }
		STATUS			current
		DESCRIPTION		"FRB1/BIST Failure."
		::=  {  trap-30920-reasoninfo 1}

END
 -- 
 -- ZTE-3GPLAT-Public-MIB.TXT
 --
